[DOCUMENT]
TITLE: High Level Requirements
UID: GSSC-HIGH-LEVEL-REQUIREMENTS
VERSION: 5.0.0
PREFIX: GSSC-HLR-

[[SECTION]]
UID: GSSC-PUBLIC-FRONTEND-HLRS
TITLE: GSSC Public Frontend

[REQUIREMENT]
UID: GSSC-HLR-1
TITLE: Public Frontend Application
STATEMENT: >>>
The GSSC Website SHALL have a public-accessible frontend application.
<<<
RELATIONS:
- TYPE: Parent
  VALUE: GSSC-OBJ-1

[[SECTION]]
UID: GSSC-PUBLIC-FEATURE-HLRS
TITLE: Public Frontend Features

[REQUIREMENT]
UID: GSSC-HLR-2
TITLE: Public Home Page
STATEMENT: >>>
The GSSC Website Public Frontend SHALL have a home page.
<<<
RELATIONS:
- TYPE: Parent
  VALUE: GSSC-OBJ-8

[REQUIREMENT]
UID: GSSC-HLR-3
TITLE: Public Membership Information Page
STATEMENT: >>>
The GSSC Website Public Frontend SHALL have a membership information page.
<<<
RELATIONS:
- TYPE: Parent
  VALUE: GSSC-OBJ-9

[REQUIREMENT]
UID: GSSC-HLR-4
TITLE: Public Leadership Page
STATEMENT: >>>
The GSSC Website Public Frontend SHALL have a leadership page.
<<<
RELATIONS:
- TYPE: Parent
  VALUE: GSSC-OBJ-10

[REQUIREMENT]
UID: GSSC-HLR-5
TITLE: Public Calendar
STATEMENT: >>>
The GSSC Website Public Frontend SHALL have a public calendar.
<<<
RELATIONS:
- TYPE: Parent
  VALUE: GSSC-OBJ-11

[REQUIREMENT]
UID: GSSC-HLR-6
TITLE: Public Research Tools Page
STATEMENT: >>>
The GSSC Website Public Frontend SHALL have a public research tools page.
<<<
RELATIONS:
- TYPE: Parent
  VALUE: GSSC-OBJ-12

[REQUIREMENT]
UID: GSSC-HLR-7
TITLE: Public Publications Page
STATEMENT: >>>
The GSSC Website Public Frontend SHALL have a publications page.
<<<
RELATIONS:
- TYPE: Parent
  VALUE: GSSC-OBJ-13

[REQUIREMENT]
UID: GSSC-HLR-8
TITLE: Public Newsletters Page
STATEMENT: >>>
The GSSC Website Public Frontend SHALL have a newsletters page.
<<<
RELATIONS:
- TYPE: Parent
  VALUE: GSSC-OBJ-14

[REQUIREMENT]
UID: GSSC-HLR-9
TITLE: Members Access
STATEMENT: >>>
The GSSC Website Public Frontend SHALL provide access for to the Member Frontend.
<<<
RELATIONS:
- TYPE: Parent
  VALUE: GSSC-OBJ-2

[[/SECTION]]

[[/SECTION]]

[[SECTION]]
UID: GSSC-MEMBER-FRONTEND-HLRS
TITLE: GSSC Member Frontend

[[/SECTION]]

[[SECTION]]
UID: GSSC-BACKEND-HLRS
TITLE: GSSC Unified API

[[/SECTION]]
