[DOCUMENT]
TITLE: Public Low Level Requirements
UID: GSSC-PUBLIC-LOW-LEVEL-REQUIREMENTS
VERSION: 5.0.0

[GRAMMAR]
ELEMENTS:
- TAG: TEXT
  FIELDS:
  - TITLE: UID
    TYPE: String
    REQUIRED: False
  - TITLE: STATEMENT
    TYPE: String
    REQUIRED: True
- TAG: SECTION
  PROPERTIES:
    IS_COMPOSITE: True
    PREFIX: None
    VIEW_STYLE: Narrative
  FIELDS:
  - TITLE: UID
    TYPE: String
    REQUIRED: False
  - TITLE: TITLE
    TYPE: String
    REQUIRED: True
- TAG: REQUIREMENT
  PROPERTIES:
    PREFIX: GSSC-PLLR-
    VIEW_STYLE: Table
  FIELDS:
  - TITLE: UID
    TYPE: String
    REQUIRED: True
  - TITLE: TITLE
    TYPE: String
    REQUIRED: True
  - TITLE: STATEMENT
    TYPE: String
    REQUIRED: True
  - TITLE: RATIONALE
    TYPE: String
    REQUIRED: True
  - TITLE: COMMENT
    TYPE: String
    REQUIRED: False
  - TITLE: DERIVED
    TYPE: SingleChoice(True, False)
    REQUIRED: True
  - TITLE: VERIFICATION_METHOD
    TYPE: SingleChoice(Test, Inspection)
    REQUIRED: True
  - TITLE: CHANGE_DRIVER
    TYPE: String
    REQUIRED: True
  - TITLE: REVIEW_STATUS
    TYPE: SingleChoice(Changed, Approved, Baselined)
    REQUIRED: True
  RELATIONS:
  - TYPE: Parent
    ROLE: Refines
    REVERSE_ROLE: Refined By

[[SECTION]]
UID: GSSC-PLLR-APP-ROOT
TITLE: Public App Root

[[SECTION]]
UID: GSSC-PLLR-APP-ROOT-ELEMENT
TITLE: App Root

[REQUIREMENT]
UID: GSSC-PLLR-4
TITLE: Semantic
STATEMENT: >>>
The GSSC Website Public Frontend App Root SHALL contain a Header host, an Announcements Bar when the App Root shows that bar, a Page Outlet, a Footer host, and a Prompt Overlay host.
<<<
RATIONALE: >>>
The App Root composes those subelements so Header, Footer, announcements, the active public page, and the Prompt Overlay share one shell. Header and Footer contents are separate requirements. When the App Root shows the Announcements Bar is a separate requirement. When the Prompt Overlay host shows the overlay is a separate requirement.
<<<
DERIVED: False
VERIFICATION_METHOD: Test
CHANGE_DRIVER: >>>
GSSC5-38
GSSC5-27
<<<
REVIEW_STATUS: Approved
RELATIONS:
- TYPE: Parent
  VALUE: GSSC-PHLR-128
  ROLE: Refines

[REQUIREMENT]
UID: GSSC-PLLR-20
TITLE: Syntactic
STATEMENT: >>>
The GSSC Website Public Frontend App Root SHALL fill the entire viewport.
<<<
RATIONALE: >>>
The App Root is the outermost shell of the public page. Filling the viewport gives Header, page content, and Footer a full-page layout that resizes with the viewport.
<<<
DERIVED: False
VERIFICATION_METHOD: Test
CHANGE_DRIVER: GSSC5-38
REVIEW_STATUS: Approved
RELATIONS:
- TYPE: Parent
  VALUE: GSSC-PHLR-128
  ROLE: Refines

[REQUIREMENT]
UID: GSSC-PLLR-21
TITLE: Lexical
STATEMENT: >>>
The GSSC Website Public Frontend App Root SHALL use the white theme token for its background and the sans-serif theme font for its text.
<<<
RATIONALE: >>>
The outermost site layer uses a white background and a sans-serif default. Theme tokens supply those values.
<<<
DERIVED: False
VERIFICATION_METHOD: Test
CHANGE_DRIVER: GSSC5-38
REVIEW_STATUS: Approved
RELATIONS:
- TYPE: Parent
  VALUE: GSSC-PHLR-128
  ROLE: Refines

[[/SECTION]]

[[SECTION]]
UID: GSSC-PLLR-HEADER-HOST
TITLE: Header Host

[REQUIREMENT]
UID: GSSC-PLLR-5
TITLE: Semantic
STATEMENT: >>>
The Header host SHALL hold the Public Frontend Header.
<<<
RATIONALE: >>>
The App Root supplies a host so Header implementation mounts in the public shell. Header contents are separate requirements.
<<<
DERIVED: False
VERIFICATION_METHOD: Test
CHANGE_DRIVER: GSSC5-38
REVIEW_STATUS: Approved
RELATIONS:
- TYPE: Parent
  VALUE: GSSC-PHLR-44
  ROLE: Refines

[REQUIREMENT]
UID: GSSC-PLLR-22
TITLE: Syntactic
STATEMENT: >>>
The Header host SHALL stick to the top of the viewport while the visitor scrolls.
<<<
RATIONALE: >>>
Common public pages keep the Header at the top. Sticking the host keeps that top placement as the visitor scrolls.
<<<
DERIVED: False
VERIFICATION_METHOD: Test
CHANGE_DRIVER: GSSC5-38
REVIEW_STATUS: Approved
RELATIONS:
- TYPE: Parent
  VALUE: GSSC-PHLR-44
  ROLE: Refines

[REQUIREMENT]
UID: GSSC-PLLR-23
TITLE: Lexical
STATEMENT: >>>
The Header host SHALL inherit the App Root font and text color theme tokens.
<<<
RATIONALE: >>>
The Header host is an empty mount for Header contents. It inherits App Root type tokens so the shell stays consistent until Header paints its own presentation. Independent Header host colors are not set yet.
<<<
DERIVED: False
VERIFICATION_METHOD: Test
CHANGE_DRIVER: GSSC5-38
REVIEW_STATUS: Approved
RELATIONS:
- TYPE: Parent
  VALUE: GSSC-PHLR-44
  ROLE: Refines

[[/SECTION]]

[[SECTION]]
UID: GSSC-PLLR-FOOTER-HOST
TITLE: Footer Host

[REQUIREMENT]
UID: GSSC-PLLR-6
TITLE: Semantic
STATEMENT: >>>
The Footer host SHALL hold the Public Frontend Footer.
<<<
RATIONALE: >>>
The App Root supplies a host so Footer implementation mounts in the public shell. Footer contents are separate requirements.
<<<
DERIVED: False
VERIFICATION_METHOD: Test
CHANGE_DRIVER: GSSC5-38
REVIEW_STATUS: Approved
RELATIONS:
- TYPE: Parent
  VALUE: GSSC-PHLR-46
  ROLE: Refines

[REQUIREMENT]
UID: GSSC-PLLR-24
TITLE: Syntactic
STATEMENT: >>>
The Footer host SHALL sit at the bottom of the App Root.
<<<
RATIONALE: >>>
Common public pages place the Footer at the bottom. The host anchors that placement in the App Root.
<<<
DERIVED: False
VERIFICATION_METHOD: Test
CHANGE_DRIVER: GSSC5-38
REVIEW_STATUS: Approved
RELATIONS:
- TYPE: Parent
  VALUE: GSSC-PHLR-46
  ROLE: Refines

[REQUIREMENT]
UID: GSSC-PLLR-25
TITLE: Lexical
STATEMENT: >>>
The Footer host SHALL inherit the App Root font and text color theme tokens.
<<<
RATIONALE: >>>
The Footer host is an empty mount for Footer contents. It inherits App Root type tokens so the shell stays consistent until Footer paints its own presentation. Independent Footer host colors are not set yet.
<<<
DERIVED: False
VERIFICATION_METHOD: Test
CHANGE_DRIVER: GSSC5-38
REVIEW_STATUS: Approved
RELATIONS:
- TYPE: Parent
  VALUE: GSSC-PHLR-46
  ROLE: Refines

[[/SECTION]]

[[SECTION]]
UID: GSSC-PLLR-PROMPT-OVERLAY-HOST
TITLE: Prompt Overlay Host

[REQUIREMENT]
UID: GSSC-PLLR-104
TITLE: Semantic
STATEMENT: >>>
The Prompt Overlay host SHALL hold the Public Prompt Overlay when that overlay is open.
<<<
RATIONALE: >>>
No Public Frontend PIR defines a prompt overlay. The App Root supplies a host so the Prompt Overlay mounts in the public shell when open. Overlay Contents are separate requirements. Derived because PIRs do not define this host.
<<<
COMMENT: >>>
Proposed for owner review (GSSC5-27). REVIEW_STATUS stays Changed until owner approval.
<<<
DERIVED: True
VERIFICATION_METHOD: Test
CHANGE_DRIVER: GSSC5-27
REVIEW_STATUS: Approved

[REQUIREMENT]
UID: GSSC-PLLR-105
TITLE: Syntactic
STATEMENT: >>>
The Prompt Overlay host SHALL overlay the Public Prompt Overlay on the App Root above the Header, Page Outlet, and Footer while leaving those App Root elements in place.
<<<
RATIONALE: >>>
Overlaying the prompt on the App Root keeps the prompt above page content without shifting Header, Page Outlet, or Footer layout.
<<<
COMMENT: >>>
Proposed for owner review (GSSC5-27).
<<<
DERIVED: True
VERIFICATION_METHOD: Test
CHANGE_DRIVER: GSSC5-27
REVIEW_STATUS: Approved

[REQUIREMENT]
UID: GSSC-PLLR-106
TITLE: Lexical
STATEMENT: >>>
The Prompt Overlay host SHALL inherit the App Root font and text color theme tokens.
<<<
RATIONALE: >>>
The Prompt Overlay host is a mount for the Prompt Overlay. It inherits App Root type tokens so the shell stays consistent until the overlay paints its own presentation. Independent host colors are not set yet.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PAGE-OUTLET
TITLE: Page Outlet

[REQUIREMENT]
UID: GSSC-PLLR-7
TITLE: Semantic
STATEMENT: >>>
The Page Outlet SHALL render the active public page.
<<<
RATIONALE: >>>
Public pages mount through the Page Outlet so each page shares the App Root shell. Page contents are separate requirements.
<<<
DERIVED: False
VERIFICATION_METHOD: Test
CHANGE_DRIVER: GSSC5-38
REVIEW_STATUS: Approved
RELATIONS:
- TYPE: Parent
  VALUE: GSSC-PHLR-128
  ROLE: Refines

[REQUIREMENT]
UID: GSSC-PLLR-26
TITLE: Syntactic
STATEMENT: >>>
The Page Outlet SHALL sit between the Header host and the Footer host and SHALL grow to fill the remaining App Root space.
<<<
RATIONALE: >>>
Placing the outlet between the hosts and letting it grow keeps Header and Footer at the edges while page content uses the middle of the shell as the viewport resizes.
<<<
DERIVED: False
VERIFICATION_METHOD: Test
CHANGE_DRIVER: GSSC5-38
REVIEW_STATUS: Approved
RELATIONS:
- TYPE: Parent
  VALUE: GSSC-PHLR-128
  ROLE: Refines

[REQUIREMENT]
UID: GSSC-PLLR-27
TITLE: Lexical
STATEMENT: >>>
The Page Outlet SHALL inherit the App Root font and text color theme tokens.
<<<
RATIONALE: >>>
The Page Outlet is a mount for page contents. It inherits App Root type tokens so pages share the shell defaults until a page sets its own presentation. Independent Page Outlet colors are not set yet.
<<<
DERIVED: False
VERIFICATION_METHOD: Test
CHANGE_DRIVER: GSSC5-38
REVIEW_STATUS: Approved
RELATIONS:
- TYPE: Parent
  VALUE: GSSC-PHLR-128
  ROLE: Refines

[[/SECTION]]

[[SECTION]]
UID: GSSC-PLLR-ANNOUNCEMENTS-BAR
TITLE: Announcements Bar

[REQUIREMENT]
UID: GSSC-PLLR-15
TITLE: Semantic
STATEMENT: >>>
The Announcements Bar SHALL display the title and text of each urgent public announcement it receives, and SHALL open the home page announcements display focused on an announcement when the visitor selects that announcement.
<<<
RATIONALE: >>>
The bar presents urgent announcement contents and routes the visitor to that announcement on the home page. Title and text refine the urgent announcement contents. Selection refines urgent announcement selection.
<<<
DERIVED: False
VERIFICATION_METHOD: Test
CHANGE_DRIVER: GSSC5-38
REVIEW_STATUS: Approved
RELATIONS:
- TYPE: Parent
  VALUE: GSSC-PHLR-30
  ROLE: Refines
- TYPE: Parent
  VALUE: GSSC-PHLR-31
  ROLE: Refines
- TYPE: Parent
  VALUE: GSSC-PHLR-34
  ROLE: Refines

[REQUIREMENT]
UID: GSSC-PLLR-16
TITLE: Syntactic
STATEMENT: >>>
The App Root SHALL show the Announcements Bar between the Header host and the Page Outlet on every public page other than the home page when there is an urgent public announcement to display, and SHALL omit the Announcements Bar on the home page.
<<<
RATIONALE: >>>
The Urgent Announcement Container belongs on non-home public pages when an urgent announcement exists. The home page uses the Announcements Display instead. Placement under the Header host keeps the bar in the shared shell.
<<<
DERIVED: False
VERIFICATION_METHOD: Test
CHANGE_DRIVER: GSSC5-38
REVIEW_STATUS: Approved
RELATIONS:
- TYPE: Parent
  VALUE: GSSC-PHLR-27
  ROLE: Refines
- TYPE: Parent
  VALUE: GSSC-PHLR-47
  ROLE: Refines

[REQUIREMENT]
UID: GSSC-PLLR-17
TITLE: Lexical
STATEMENT: >>>
The Announcements Bar SHALL use the cream theme token for its background, the gray theme token for its bottom border, the dark-green theme token for announcement titles, and the dark-brown theme token for announcement text.
<<<
RATIONALE: >>>
Theme tokens keep announcement presentation aligned with the organization palette. A fuller color role map for the bar is not set yet beyond these token choices.
<<<
DERIVED: False
VERIFICATION_METHOD: Test
CHANGE_DRIVER: GSSC5-38
REVIEW_STATUS: Approved
RELATIONS:
- TYPE: Parent
  VALUE: GSSC-PHLR-47
  ROLE: Refines

[[/SECTION]]

[[/SECTION]]

[[SECTION]]
UID: GSSC-PLLR-MODULES
TITLE: Modules

[[SECTION]]
UID: GSSC-PLLR-HEADER
TITLE: Public Header

[[SECTION]]
UID: GSSC-PLLR-HEADER-ELEMENT
TITLE: Header

[REQUIREMENT]
UID: GSSC-PLLR-46
TITLE: Semantic
STATEMENT: >>>
The GSSC Website Public Frontend Header SHALL present the Header Logo, the Header Organization Name when the layout permits, the Header account-access controls, the Header Contact control, and the Header Site Search control.
<<<
RATIONALE: >>>
The Header composes those displayed elements in the Header host. Each element's behavior is a separate requirement.
<<<
COMMENT: >>>
Proposed for owner review (GSSC5-22). REVIEW_STATUS stays Changed until owner approval.
<<<
DERIVED: True
VERIFICATION_METHOD: Test
CHANGE_DRIVER: GSSC5-22
REVIEW_STATUS: Approved

[REQUIREMENT]
UID: GSSC-PLLR-47
TITLE: Syntactic
STATEMENT: >>>
The GSSC Website Public Frontend Header SHALL fill the Header host and arrange identity and Header actions in a horizontal bar that wraps as the viewport narrows.
<<<
RATIONALE: >>>
The Header host already sticks to the top of the viewport. Filling that host and wrapping the bar keeps Header contents available as the page resizes.
<<<
COMMENT: >>>
Proposed for owner review (GSSC5-22).
<<<
DERIVED: True
VERIFICATION_METHOD: Test
CHANGE_DRIVER: GSSC5-22
REVIEW_STATUS: Approved

[REQUIREMENT]
UID: GSSC-PLLR-48
TITLE: Lexical
STATEMENT: >>>
The GSSC Website Public Frontend Header SHALL use the light-green theme token for its background, the gray theme token for a thicker bottom border, and the dark-green theme token for its text.
<<<
RATIONALE: >>>
Theme tokens keep Header presentation aligned with the organization palette. A fuller color role map for the Header is not set yet beyond these token choices.
<<<
COMMENT: >>>
Thicker bottom border approved for GSSC5-22. Color tokens remain provisional until a full color role map exists.
<<<
DERIVED: True
VERIFICATION_METHOD: Test
CHANGE_DRIVER: GSSC5-22
REVIEW_STATUS: Approved

[[/SECTION]]

[[SECTION]]
UID: GSSC-PLLR-HEADER-LOGO
TITLE: Logo

[REQUIREMENT]
UID: GSSC-PLLR-49
TITLE: Semantic
STATEMENT: >>>
The Header Logo SHALL display the GSSC Logo, and selection of the Header Logo SHALL open the public home page.
<<<
RATIONALE: >>>
The Header always includes the GSSC Logo so the visitor can identify the society. Selecting the logo returns the visitor to the public home page.
<<<
COMMENT: >>>
Placeholder SVG mark is acceptable until brand artwork lands in GSSC5-46 (logo branding across favicon, Header, and Footer).
<<<
DERIVED: False
VERIFICATION_METHOD: Test
CHANGE_DRIVER: GSSC5-22
REVIEW_STATUS: Approved
RELATIONS:
- TYPE: Parent
  VALUE: GSSC-PHLR-1
  ROLE: Refines

[REQUIREMENT]
UID: GSSC-PLLR-50
TITLE: Syntactic
STATEMENT: >>>
The Header Logo SHALL appear at the start of the Header in every layout.
<<<
RATIONALE: >>>
Leading placement keeps the logo visible whether or not the organization name also fits.
<<<
DERIVED: False
VERIFICATION_METHOD: Test
CHANGE_DRIVER: GSSC5-22
REVIEW_STATUS: Approved
RELATIONS:
- TYPE: Parent
  VALUE: GSSC-PHLR-1
  ROLE: Refines

[REQUIREMENT]
UID: GSSC-PLLR-51
TITLE: Lexical
STATEMENT: >>>
The Header Logo SHALL use the dark-green theme token for its mark color.
<<<
RATIONALE: >>>
A single theme token keeps the mark readable on the Header background until a brand color role is set.
<<<
DERIVED: False
VERIFICATION_METHOD: Test
CHANGE_DRIVER: GSSC5-22
REVIEW_STATUS: Approved
RELATIONS:
- TYPE: Parent
  VALUE: GSSC-PHLR-1
  ROLE: Refines

[[/SECTION]]

[[SECTION]]
UID: GSSC-PLLR-HEADER-ORG-NAME
TITLE: Organization Name

[REQUIREMENT]
UID: GSSC-PLLR-52
TITLE: Semantic
STATEMENT: >>>
The Header Organization Name SHALL display the society's organization name or organization acronym from the Society Contact service when the layout permits.
<<<
RATIONALE: >>>
The Header shows one organization-name form at a time from the Society Contact service. Which form is visible by layout width is a separate Lexical requirement.
<<<
COMMENT: >>>
Owner-approved layout bands (GSSC5-22): full name at medium and above; acronym from small up to under medium; omit below small (logo remains). Brand artwork deferred to GSSC5-46.
<<<
DERIVED: False
VERIFICATION_METHOD: Test
CHANGE_DRIVER: GSSC5-22
REVIEW_STATUS: Approved
RELATIONS:
- TYPE: Parent
  VALUE: GSSC-PHLR-19
  ROLE: Refines

[REQUIREMENT]
UID: GSSC-PLLR-53
TITLE: Syntactic
STATEMENT: >>>
The Header Organization Name SHALL appear beside the Header Logo when the layout permits a name, and SHALL be omitted from the Header when the layout does not permit a name.
<<<
RATIONALE: >>>
Placement beside the logo keeps identity together. Omitting the name on a narrow layout leaves the logo as the identity mark.
<<<
DERIVED: False
VERIFICATION_METHOD: Test
CHANGE_DRIVER: GSSC5-22
REVIEW_STATUS: Approved
RELATIONS:
- TYPE: Parent
  VALUE: GSSC-PHLR-19
  ROLE: Refines

[REQUIREMENT]
UID: GSSC-PLLR-54
TITLE: Lexical
STATEMENT: >>>
The Header Organization Name SHALL use the sans-serif theme font, a medium font weight, and the dark-green theme token for its text color, SHALL show the organization name at medium and above, SHALL show the organization acronym from small up to under medium, and SHALL omit the name below small.
<<<
RATIONALE: >>>
Those tokens keep the name aligned with Header text. The width bands keep a readable identity mark as the viewport narrows or widens.
<<<
DERIVED: False
VERIFICATION_METHOD: Test
CHANGE_DRIVER: GSSC5-22
REVIEW_STATUS: Approved
RELATIONS:
- TYPE: Parent
  VALUE: GSSC-PHLR-19
  ROLE: Refines

[[/SECTION]]

[[SECTION]]
UID: GSSC-PLLR-HEADER-LOGIN
TITLE: Login

[REQUIREMENT]
UID: GSSC-PLLR-55
TITLE: Semantic
STATEMENT: >>>
When no member is logged in, the Header Login control SHALL navigate the visitor to the members-only application.
<<<
RATIONALE: >>>
Login on the public Header is navigation to the Member Frontend. Member Frontend UI is out of this requirement's scope.
<<<
COMMENT: >>>
Proposed for owner review (GSSC5-22). Proposed default members origin for local development: http://localhost:4201.
<<<
DERIVED: False
VERIFICATION_METHOD: Test
CHANGE_DRIVER: GSSC5-22
REVIEW_STATUS: Approved
RELATIONS:
- TYPE: Parent
  VALUE: GSSC-PHLR-2
  ROLE: Refines

[REQUIREMENT]
UID: GSSC-PLLR-56
TITLE: Syntactic
STATEMENT: >>>
The Header Login control SHALL appear first among the Header right-side action controls when no member is logged in, SHALL be omitted when a member is logged in, and SHALL be separated from the following right-side text control by a vertical divider.
<<<
RATIONALE: >>>
Owner-approved right-side order is Login, then Contact, then Site Search. Vertical dividers separate right-side text items. The Greeting replaces Login when a member is logged in.
<<<
DERIVED: False
VERIFICATION_METHOD: Test
CHANGE_DRIVER: GSSC5-22
REVIEW_STATUS: Approved
RELATIONS:
- TYPE: Parent
  VALUE: GSSC-PHLR-2
  ROLE: Refines

[REQUIREMENT]
UID: GSSC-PLLR-57
TITLE: Lexical
STATEMENT: >>>
The Header Login control SHALL use the sans-serif theme font and the dark-green theme token for its text color.
<<<
RATIONALE: >>>
Account-access controls share Header text tokens until a fuller control style map exists.
<<<
DERIVED: False
VERIFICATION_METHOD: Test
CHANGE_DRIVER: GSSC5-22
REVIEW_STATUS: Approved
RELATIONS:
- TYPE: Parent
  VALUE: GSSC-PHLR-2
  ROLE: Refines

[[/SECTION]]

[[SECTION]]
UID: GSSC-PLLR-HEADER-MEMBER-ACCESS
TITLE: Member Access

[REQUIREMENT]
UID: GSSC-PLLR-58
TITLE: Semantic
STATEMENT: >>>
When a member is logged in, the Header Member Access control SHALL navigate the visitor to the members-only application.
<<<
RATIONALE: >>>
A logged-in member reaches the Member Frontend through Member Access instead of Login.
<<<
DERIVED: False
VERIFICATION_METHOD: Test
CHANGE_DRIVER: GSSC5-22
REVIEW_STATUS: Approved
RELATIONS:
- TYPE: Parent
  VALUE: GSSC-PHLR-18
  ROLE: Refines

[REQUIREMENT]
UID: GSSC-PLLR-59
TITLE: Syntactic
STATEMENT: >>>
The Header Member Access control SHALL appear in the Header Greeting dropdown when a member is logged in, and SHALL be omitted when no member is logged in.
<<<
RATIONALE: >>>
Member Access is reached from the Greeting dropdown rather than replacing Login as a top-level control.
<<<
DERIVED: False
VERIFICATION_METHOD: Test
CHANGE_DRIVER: GSSC5-22
REVIEW_STATUS: Approved
RELATIONS:
- TYPE: Parent
  VALUE: GSSC-PHLR-18
  ROLE: Refines

[REQUIREMENT]
UID: GSSC-PLLR-60
TITLE: Lexical
STATEMENT: >>>
The Header Member Access control SHALL use the sans-serif theme font and the dark-green theme token for its text color.
<<<
RATIONALE: >>>
Account-access controls share Header text tokens until a fuller control style map exists.
<<<
DERIVED: False
VERIFICATION_METHOD: Test
CHANGE_DRIVER: GSSC5-22
REVIEW_STATUS: Approved
RELATIONS:
- TYPE: Parent
  VALUE: GSSC-PHLR-18
  ROLE: Refines

[[/SECTION]]

[[SECTION]]
UID: GSSC-PLLR-HEADER-GREETING
TITLE: Greeting

[REQUIREMENT]
UID: GSSC-PLLR-61
TITLE: Semantic
STATEMENT: >>>
When a member is logged in with a valid members-only application session, the Header Greeting SHALL display a greeting that includes that member's name.
<<<
RATIONALE: >>>
The greeting shows a logged-in member that the Header recognizes the session and identifies the member by name.
<<<
COMMENT: >>>
Greeting form is Hello, followed by the member name (GSSC5-22).
<<<
DERIVED: False
VERIFICATION_METHOD: Test
CHANGE_DRIVER: GSSC5-22
REVIEW_STATUS: Approved
RELATIONS:
- TYPE: Parent
  VALUE: GSSC-PHLR-8
  ROLE: Refines

[REQUIREMENT]
UID: GSSC-PLLR-62
TITLE: Syntactic
STATEMENT: >>>
The Header Greeting SHALL appear first among the Header right-side action controls in place of the Header Login control when a member is logged in, SHALL be omitted when no member is logged in, SHALL open a dropdown on hover that contains the Header Member Access and Header Logout controls, and SHALL be separated from the following right-side text control by a vertical divider.
<<<
RATIONALE: >>>
The Greeting replaces Login in the right-side order. Hover reveals Members site access and Logout without crowding the Header bar.
<<<
DERIVED: False
VERIFICATION_METHOD: Test
CHANGE_DRIVER: GSSC5-22
REVIEW_STATUS: Approved
RELATIONS:
- TYPE: Parent
  VALUE: GSSC-PHLR-8
  ROLE: Refines

[REQUIREMENT]
UID: GSSC-PLLR-63
TITLE: Lexical
STATEMENT: >>>
The Header Greeting SHALL use the sans-serif theme font and the dark-green theme token for its text color.
<<<
RATIONALE: >>>
The Greeting shares Header action text tokens so it reads with Login, Contact, and related controls.
<<<
DERIVED: False
VERIFICATION_METHOD: Test
CHANGE_DRIVER: GSSC5-22
REVIEW_STATUS: Approved
RELATIONS:
- TYPE: Parent
  VALUE: GSSC-PHLR-8
  ROLE: Refines

[[/SECTION]]

[[SECTION]]
UID: GSSC-PLLR-HEADER-LOGOUT
TITLE: Logout

[REQUIREMENT]
UID: GSSC-PLLR-64
TITLE: Semantic
STATEMENT: >>>
When a member is logged in, the Header Logout control SHALL end that member's members-only application session and leave the visitor on the public page.
<<<
RATIONALE: >>>
Logout ends the Member Frontend session through the existing backend logout and keeps the visitor on the current public page.
<<<
DERIVED: False
VERIFICATION_METHOD: Test
CHANGE_DRIVER: GSSC5-22
REVIEW_STATUS: Approved
RELATIONS:
- TYPE: Parent
  VALUE: GSSC-PHLR-9
  ROLE: Refines

[REQUIREMENT]
UID: GSSC-PLLR-65
TITLE: Syntactic
STATEMENT: >>>
The Header Logout control SHALL appear in the Header Greeting dropdown when a member is logged in, and SHALL be omitted when no member is logged in.
<<<
RATIONALE: >>>
Logout sits with Member Access in the Greeting dropdown for logged-in visitors.
<<<
DERIVED: False
VERIFICATION_METHOD: Test
CHANGE_DRIVER: GSSC5-22
REVIEW_STATUS: Approved
RELATIONS:
- TYPE: Parent
  VALUE: GSSC-PHLR-9
  ROLE: Refines

[REQUIREMENT]
UID: GSSC-PLLR-66
TITLE: Lexical
STATEMENT: >>>
The Header Logout control SHALL use the sans-serif theme font and the dark-green theme token for its text color.
<<<
RATIONALE: >>>
Account-access controls share Header text tokens until a fuller control style map exists.
<<<
DERIVED: False
VERIFICATION_METHOD: Test
CHANGE_DRIVER: GSSC5-22
REVIEW_STATUS: Approved
RELATIONS:
- TYPE: Parent
  VALUE: GSSC-PHLR-9
  ROLE: Refines

[[/SECTION]]

[[SECTION]]
UID: GSSC-PLLR-HEADER-CONTACT
TITLE: Contact

[REQUIREMENT]
UID: GSSC-PLLR-67
TITLE: Semantic
STATEMENT: >>>
The Header Contact control SHALL open the Public Contact Overlay so a visitor can draft a message to the organization.
<<<
RATIONALE: >>>
Header Contact is the Header's path into the Public Contact Overlay. Overlay contents are separate requirements.
<<<
COMMENT: >>>
Header open hook from GSSC5-22. Public Contact Overlay Contents are GSSC5-31.
<<<
DERIVED: False
VERIFICATION_METHOD: Test
CHANGE_DRIVER: GSSC5-22
REVIEW_STATUS: Approved
RELATIONS:
- TYPE: Parent
  VALUE: GSSC-PHLR-3
  ROLE: Refines

[REQUIREMENT]
UID: GSSC-PLLR-68
TITLE: Syntactic
STATEMENT: >>>
The Header Contact control SHALL appear in the Header right-side action controls after the Header Login control or Header Greeting and before the Header Site Search control, and SHALL be separated from adjacent right-side text controls by vertical dividers.
<<<
RATIONALE: >>>
Owner-approved right-side order is Login or Greeting, then Contact, then Site Search. Dividers separate right-side text items.
<<<
DERIVED: False
VERIFICATION_METHOD: Test
CHANGE_DRIVER: GSSC5-22
REVIEW_STATUS: Approved
RELATIONS:
- TYPE: Parent
  VALUE: GSSC-PHLR-3
  ROLE: Refines

[REQUIREMENT]
UID: GSSC-PLLR-69
TITLE: Lexical
STATEMENT: >>>
The Header Contact control SHALL use the sans-serif theme font and the dark-green theme token for its text color.
<<<
RATIONALE: >>>
Header action controls share Header text tokens until a fuller control style map exists.
<<<
DERIVED: False
VERIFICATION_METHOD: Test
CHANGE_DRIVER: GSSC5-22
REVIEW_STATUS: Approved
RELATIONS:
- TYPE: Parent
  VALUE: GSSC-PHLR-3
  ROLE: Refines

[[/SECTION]]

[[SECTION]]
UID: GSSC-PLLR-HEADER-SITE-SEARCH
TITLE: Site Search

[REQUIREMENT]
UID: GSSC-PLLR-70
TITLE: Semantic
STATEMENT: >>>
The Header Site Search control SHALL toggle a Header search presentation open and closed. While the search presentation is open, the control SHALL provide a way for the visitor to dismiss it, including by choosing the control again or by pressing Escape.
<<<
RATIONALE: >>>
The Header search control opens and closes search from the Header. The full search widget contents are a separate feature.
<<<
COMMENT: >>>
Placeholder open presentation is acceptable in GSSC5-22. Search widget UI is deferred to GSSC5-47.
<<<
DERIVED: False
VERIFICATION_METHOD: Test
CHANGE_DRIVER: GSSC5-22
REVIEW_STATUS: Approved
RELATIONS:
- TYPE: Parent
  VALUE: GSSC-PHLR-4
  ROLE: Refines

[REQUIREMENT]
UID: GSSC-PLLR-71
TITLE: Syntactic
STATEMENT: >>>
The Header Site Search control SHALL appear last among the Header right-side action controls, SHALL present a search icon when the search presentation is closed, and SHALL present a close icon when the search presentation is open.
<<<
RATIONALE: >>>
Owner-approved right-side order ends with Site Search. Icon state shows whether search is open.
<<<
DERIVED: False
VERIFICATION_METHOD: Test
CHANGE_DRIVER: GSSC5-22
REVIEW_STATUS: Approved
RELATIONS:
- TYPE: Parent
  VALUE: GSSC-PHLR-4
  ROLE: Refines

[REQUIREMENT]
UID: GSSC-PLLR-72
TITLE: Lexical
STATEMENT: >>>
The Header Site Search control SHALL use the dark-green theme token for its icon color, rounded corners, the gray theme token for its background on hover, the white theme token for the open search presentation background, and the gray theme token for that presentation's border.
<<<
RATIONALE: >>>
Icon and placeholder panel tokens keep search readable on the Header until the search widget defines its own presentation in GSSC5-47. Rounded corners and gray background on hover match other public icon buttons and mark the control as activatable without changing the icon color.
<<<
COMMENT: >>>
Shared icon-button chrome (rounded corners; gray hover) aligned under GSSC5-25.
<<<
DERIVED: False
VERIFICATION_METHOD: Test
CHANGE_DRIVER: >>>
GSSC5-22
GSSC5-27
GSSC5-25
<<<
REVIEW_STATUS: Approved
RELATIONS:
- TYPE: Parent
  VALUE: GSSC-PHLR-4
  ROLE: Refines

[[/SECTION]]

[[/SECTION]]

[[SECTION]]
UID: GSSC-PLLR-FOOTER
TITLE: Public Footer

[[SECTION]]
UID: GSSC-PLLR-FOOTER-ELEMENT
TITLE: Footer

[REQUIREMENT]
UID: GSSC-PLLR-28
TITLE: Semantic
STATEMENT: >>>
The Public Frontend Footer SHALL contain the Organization Name, Phone Number, Email Address, Postal Address, and Contact control.
<<<
RATIONALE: >>>
The Footer presents those society identity and contact elements together in the public shell. Each element's behavior is a separate requirement. Contact overlay contents are a separate feature.
<<<
DERIVED: False
VERIFICATION_METHOD: Test
CHANGE_DRIVER: GSSC5-23
REVIEW_STATUS: Approved
RELATIONS:
- TYPE: Parent
  VALUE: GSSC-PHLR-20
  ROLE: Refines
- TYPE: Parent
  VALUE: GSSC-PHLR-21
  ROLE: Refines
- TYPE: Parent
  VALUE: GSSC-PHLR-24
  ROLE: Refines
- TYPE: Parent
  VALUE: GSSC-PHLR-25
  ROLE: Refines
- TYPE: Parent
  VALUE: GSSC-PHLR-26
  ROLE: Refines

[REQUIREMENT]
UID: GSSC-PLLR-29
TITLE: Syntactic
STATEMENT: >>>
The Footer SHALL fill the Footer host across the full width of the App Root.
<<<
RATIONALE: >>>
Common public pages place the Footer at the bottom of the page. Filling the Footer host keeps that Footer edge-to-edge as the viewport resizes.
<<<
DERIVED: False
VERIFICATION_METHOD: Test
CHANGE_DRIVER: GSSC5-23
REVIEW_STATUS: Approved
RELATIONS:
- TYPE: Parent
  VALUE: GSSC-PHLR-46
  ROLE: Refines

[REQUIREMENT]
UID: GSSC-PLLR-30
TITLE: Lexical
STATEMENT: >>>
The Footer SHALL use the black theme token for its background and the white theme token for its default text color.
<<<
RATIONALE: >>>
Black and white theme tokens set a high-contrast Footer chrome. A fuller color role map for the Footer is not set yet beyond these token choices.
<<<
DERIVED: False
VERIFICATION_METHOD: Test
CHANGE_DRIVER: GSSC5-23
REVIEW_STATUS: Approved
RELATIONS:
- TYPE: Parent
  VALUE: GSSC-PHLR-46
  ROLE: Refines

[[/SECTION]]

[[SECTION]]
UID: GSSC-PLLR-FOOTER-ORGANIZATION-NAME
TITLE: Organization Name

[REQUIREMENT]
UID: GSSC-PLLR-31
TITLE: Semantic
STATEMENT: >>>
The Footer Organization Name SHALL display the society's organization name or organization acronym from the Society Contact service.
<<<
RATIONALE: >>>
The Footer shows one organization-name form at a time from the Society Contact service. Which form is visible by site width is a separate Lexical requirement.
<<<
DERIVED: False
VERIFICATION_METHOD: Test
CHANGE_DRIVER: GSSC5-23
REVIEW_STATUS: Approved
RELATIONS:
- TYPE: Parent
  VALUE: GSSC-PHLR-21
  ROLE: Refines

[REQUIREMENT]
UID: GSSC-PLLR-32
TITLE: Syntactic
STATEMENT: >>>
The Footer Organization Name SHALL appear at the start of the Footer content.
<<<
RATIONALE: >>>
Leading with the organization name identifies the Footer before the contact details.
<<<
DERIVED: False
VERIFICATION_METHOD: Test
CHANGE_DRIVER: GSSC5-23
REVIEW_STATUS: Approved
RELATIONS:
- TYPE: Parent
  VALUE: GSSC-PHLR-21
  ROLE: Refines

[REQUIREMENT]
UID: GSSC-PLLR-33
TITLE: Lexical
STATEMENT: >>>
The Footer Organization Name SHALL use a semibold weight and the white theme token for its text color, SHALL show the organization name at small and above, and SHALL show the organization acronym below small.
<<<
RATIONALE: >>>
Semibold white text distinguishes the organization name within the Footer. Showing the acronym below small and the full name at small and above keeps the label readable as the viewport narrows or widens.
<<<
DERIVED: False
VERIFICATION_METHOD: Test
CHANGE_DRIVER: GSSC5-23
REVIEW_STATUS: Approved
RELATIONS:
- TYPE: Parent
  VALUE: GSSC-PHLR-21
  ROLE: Refines

[[/SECTION]]

[[SECTION]]
UID: GSSC-PLLR-FOOTER-PHONE-NUMBER
TITLE: Phone Number

[REQUIREMENT]
UID: GSSC-PLLR-34
TITLE: Semantic
STATEMENT: >>>
The Footer Phone Number SHALL display the society's phone number from the Society Contact service and SHALL dial that number when the visitor selects it.
<<<
RATIONALE: >>>
The Footer shows the phone number separately from the Contact overlay and lets the visitor dial it. The Society Contact service supplies the number. This requirement does not set the current number.
<<<
DERIVED: False
VERIFICATION_METHOD: Test
CHANGE_DRIVER: GSSC5-23
REVIEW_STATUS: Approved
RELATIONS:
- TYPE: Parent
  VALUE: GSSC-PHLR-24
  ROLE: Refines

[REQUIREMENT]
UID: GSSC-PLLR-35
TITLE: Syntactic
STATEMENT: >>>
The Footer Phone Number SHALL appear as a telephone link with the other society contact details in the Footer.
<<<
RATIONALE: >>>
A telephone link groups the phone number with the other contact details and gives selection a dial target.
<<<
DERIVED: False
VERIFICATION_METHOD: Test
CHANGE_DRIVER: GSSC5-23
REVIEW_STATUS: Approved
RELATIONS:
- TYPE: Parent
  VALUE: GSSC-PHLR-24
  ROLE: Refines

[REQUIREMENT]
UID: GSSC-PLLR-36
TITLE: Lexical
STATEMENT: >>>
The Footer Phone Number SHALL use a normal weight and the white theme token for its text color, with no underline except on hover.
<<<
RATIONALE: >>>
Normal-weight white text keeps the telephone link readable on the Footer background. Underline on hover marks it as activatable without a default underline. A fuller type scale is not set yet beyond this weight and token choice.
<<<
DERIVED: False
VERIFICATION_METHOD: Test
CHANGE_DRIVER: GSSC5-23
REVIEW_STATUS: Approved
RELATIONS:
- TYPE: Parent
  VALUE: GSSC-PHLR-24
  ROLE: Refines

[[/SECTION]]

[[SECTION]]
UID: GSSC-PLLR-FOOTER-EMAIL-ADDRESS
TITLE: Email Address

[REQUIREMENT]
UID: GSSC-PLLR-37
TITLE: Semantic
STATEMENT: >>>
The Footer Email Address SHALL display the society's email address from the Society Contact service and SHALL open a draft message to that address when the visitor selects it.
<<<
RATIONALE: >>>
The Footer shows the email address separately from the Contact overlay and lets the visitor open a draft to that address. The Society Contact service supplies the address. This requirement does not set the current address.
<<<
DERIVED: False
VERIFICATION_METHOD: Test
CHANGE_DRIVER: GSSC5-23
REVIEW_STATUS: Approved
RELATIONS:
- TYPE: Parent
  VALUE: GSSC-PHLR-25
  ROLE: Refines

[REQUIREMENT]
UID: GSSC-PLLR-38
TITLE: Syntactic
STATEMENT: >>>
The Footer Email Address SHALL appear as a mail link with the other society contact details in the Footer.
<<<
RATIONALE: >>>
A mail link groups the email address with the other contact details and gives selection a draft-message target.
<<<
DERIVED: False
VERIFICATION_METHOD: Test
CHANGE_DRIVER: GSSC5-23
REVIEW_STATUS: Approved
RELATIONS:
- TYPE: Parent
  VALUE: GSSC-PHLR-25
  ROLE: Refines

[REQUIREMENT]
UID: GSSC-PLLR-39
TITLE: Lexical
STATEMENT: >>>
The Footer Email Address SHALL use a normal weight and the white theme token for its text color, with no underline except on hover.
<<<
RATIONALE: >>>
Normal-weight white text keeps the mail link readable on the Footer background. Underline on hover marks it as activatable without a default underline. A fuller type scale is not set yet beyond this weight and token choice.
<<<
DERIVED: False
VERIFICATION_METHOD: Test
CHANGE_DRIVER: GSSC5-23
REVIEW_STATUS: Approved
RELATIONS:
- TYPE: Parent
  VALUE: GSSC-PHLR-25
  ROLE: Refines

[[/SECTION]]

[[SECTION]]
UID: GSSC-PLLR-FOOTER-POSTAL-ADDRESS
TITLE: Postal Address

[REQUIREMENT]
UID: GSSC-PLLR-40
TITLE: Semantic
STATEMENT: >>>
The Footer Postal Address SHALL display the society's postal address from the Society Contact service.
<<<
RATIONALE: >>>
The Footer shows the postal address separately from the Contact overlay. The Society Contact service supplies the address. This requirement does not set the current address.
<<<
DERIVED: False
VERIFICATION_METHOD: Test
CHANGE_DRIVER: GSSC5-23
REVIEW_STATUS: Approved
RELATIONS:
- TYPE: Parent
  VALUE: GSSC-PHLR-26
  ROLE: Refines

[REQUIREMENT]
UID: GSSC-PLLR-41
TITLE: Syntactic
STATEMENT: >>>
The Footer Postal Address SHALL appear with the other society contact details in the Footer.
<<<
RATIONALE: >>>
Grouping the postal address with the phone number and email address keeps society contact details together in the Footer.
<<<
DERIVED: False
VERIFICATION_METHOD: Test
CHANGE_DRIVER: GSSC5-23
REVIEW_STATUS: Approved
RELATIONS:
- TYPE: Parent
  VALUE: GSSC-PHLR-26
  ROLE: Refines

[REQUIREMENT]
UID: GSSC-PLLR-42
TITLE: Lexical
STATEMENT: >>>
The Footer Postal Address SHALL use a normal weight and the white theme token for its text color.
<<<
RATIONALE: >>>
Normal-weight white text keeps contact details readable on the Footer background. A fuller type scale is not set yet beyond this weight and token choice.
<<<
DERIVED: False
VERIFICATION_METHOD: Test
CHANGE_DRIVER: GSSC5-23
REVIEW_STATUS: Approved
RELATIONS:
- TYPE: Parent
  VALUE: GSSC-PHLR-26
  ROLE: Refines

[[/SECTION]]

[[SECTION]]
UID: GSSC-PLLR-FOOTER-CONTACT
TITLE: Contact

[REQUIREMENT]
UID: GSSC-PLLR-43
TITLE: Semantic
STATEMENT: >>>
The Footer Contact control SHALL open the Public Contact Overlay when the visitor activates it.
<<<
RATIONALE: >>>
Footer Contact opens an overlay for drafting a message to the organization. Overlay contents and layout are a separate feature.
<<<
COMMENT: >>>
Footer open hook from GSSC5-23. Public Contact Overlay Contents are GSSC5-31.
<<<
DERIVED: False
VERIFICATION_METHOD: Test
CHANGE_DRIVER: GSSC5-23
REVIEW_STATUS: Approved
RELATIONS:
- TYPE: Parent
  VALUE: GSSC-PHLR-20
  ROLE: Refines

[REQUIREMENT]
UID: GSSC-PLLR-44
TITLE: Syntactic
STATEMENT: >>>
The Footer Contact control SHALL appear as an activatable control with the society contact details in the Footer.
<<<
RATIONALE: >>>
Placing Contact with the phone number, email address, and postal address keeps every Footer contact path in one group.
<<<
DERIVED: False
VERIFICATION_METHOD: Test
CHANGE_DRIVER: GSSC5-23
REVIEW_STATUS: Approved
RELATIONS:
- TYPE: Parent
  VALUE: GSSC-PHLR-20
  ROLE: Refines

[REQUIREMENT]
UID: GSSC-PLLR-45
TITLE: Lexical
STATEMENT: >>>
The Footer Contact control SHALL use the white theme token for its text color, with no underline except on hover.
<<<
RATIONALE: >>>
White text keeps Contact aligned with other Footer text on the black Footer background. Underline on hover marks it as activatable without a default underline. A fuller color role map for controls is not set yet beyond this token choice.
<<<
DERIVED: False
VERIFICATION_METHOD: Test
CHANGE_DRIVER: GSSC5-23
REVIEW_STATUS: Approved
RELATIONS:
- TYPE: Parent
  VALUE: GSSC-PHLR-20
  ROLE: Refines

[[/SECTION]]

[[/SECTION]]

[[SECTION]]
UID: GSSC-PLLR-SECTION
TITLE: Public Section

[[SECTION]]
UID: GSSC-PLLR-SECTION-CONTAINER
TITLE: Section Container

[REQUIREMENT]
UID: GSSC-PLLR-83
TITLE: Semantic
STATEMENT: >>>
The GSSC Website Public Frontend Section Container SHALL place the Section Contents it receives: the Section Header when those Contents include a header, the Section Body, and the Section Resources when those Contents include resources.
<<<
RATIONALE: >>>
The Section Container is the placement shell for section data on public pages. Contents are the section data; the Container places them. Each placed element's behavior is a separate requirement. Page assembly and Contents APIs are separate features.
<<<
COMMENT: >>>
Derived for GSSC5-25. PIRs do not define the section Container. REVIEW_STATUS stays Changed until owner approval.
<<<
DERIVED: True
VERIFICATION_METHOD: Test
CHANGE_DRIVER: GSSC5-25
REVIEW_STATUS: Approved

[REQUIREMENT]
UID: GSSC-PLLR-84
TITLE: Syntactic
STATEMENT: >>>
The Section Container SHALL fill the width of its page content area, stack the Section Contents it places in a vertical order, apply vertical padding on the Container, and keep internal spacing between the Section Header, Section Body, and Section Resources.
<<<
RATIONALE: >>>
Full-width stacking keeps section Contents readable within the page content area as the viewport resizes. Vertical padding and spacing between Header, Body, and Resources separate those elements without crowding. Page assembly chooses where Containers appear on a page.
<<<
DERIVED: True
VERIFICATION_METHOD: Test
CHANGE_DRIVER: GSSC5-25
REVIEW_STATUS: Approved

[REQUIREMENT]
UID: GSSC-PLLR-85
TITLE: Lexical
STATEMENT: >>>
The Section Container SHALL use the white theme token for its background, the gray theme token for its border, and the dark-green theme token for its default text, with a sans-serif typeface.
<<<
RATIONALE: >>>
White background keeps the section aligned with the outermost shell. Theme tokens keep presentation in the organization palette. A fuller color role map for sections is not set yet beyond these token choices.
<<<
DERIVED: True
VERIFICATION_METHOD: Test
CHANGE_DRIVER: GSSC5-25
REVIEW_STATUS: Approved

[[/SECTION]]

[[SECTION]]
UID: GSSC-PLLR-SECTION-HEADER
TITLE: Section Header

[REQUIREMENT]
UID: GSSC-PLLR-86
TITLE: Semantic
STATEMENT: >>>
The Section Header SHALL display the header from the Section Contents when those Contents include a header.
<<<
RATIONALE: >>>
A section header identifies the section when the Contents supply one. Absent headers are omitted. This requirement does not set header wording.
<<<
DERIVED: True
VERIFICATION_METHOD: Test
CHANGE_DRIVER: GSSC5-25
REVIEW_STATUS: Approved

[REQUIREMENT]
UID: GSSC-PLLR-87
TITLE: Syntactic
STATEMENT: >>>
The Section Header SHALL appear above the Section Body inside the Section Container when the Section Contents include a header.
<<<
RATIONALE: >>>
Leading with the header keeps the section title before the body text.
<<<
DERIVED: True
VERIFICATION_METHOD: Test
CHANGE_DRIVER: GSSC5-25
REVIEW_STATUS: Approved

[REQUIREMENT]
UID: GSSC-PLLR-88
TITLE: Lexical
STATEMENT: >>>
The Section Header SHALL use a semibold weight and the dark-green theme token for its text color, at a size one and one-half times the Section Body text size.
<<<
RATIONALE: >>>
Semibold dark-green text at one and one-half times the body size distinguishes the header within the Container. A fuller type scale is not set yet beyond this relative size and token choice.
<<<
DERIVED: True
VERIFICATION_METHOD: Test
CHANGE_DRIVER: GSSC5-25
REVIEW_STATUS: Approved

[[/SECTION]]

[[SECTION]]
UID: GSSC-PLLR-SECTION-BODY
TITLE: Section Body

[REQUIREMENT]
UID: GSSC-PLLR-89
TITLE: Semantic
STATEMENT: >>>
The Section Body SHALL display the body from the Section Contents.
<<<
RATIONALE: >>>
Every section's Contents include a body. The Body presents that text in the Container. This requirement does not set body wording.
<<<
DERIVED: True
VERIFICATION_METHOD: Test
CHANGE_DRIVER: GSSC5-25
REVIEW_STATUS: Approved

[REQUIREMENT]
UID: GSSC-PLLR-90
TITLE: Syntactic
STATEMENT: >>>
The Section Body SHALL appear below the Section Header when a Section Header is present, and otherwise at the start of the Section Contents inside the Section Container.
<<<
RATIONALE: >>>
The body follows the header when a header exists, and starts the Contents when it does not, so reading order stays consistent.
<<<
DERIVED: True
VERIFICATION_METHOD: Test
CHANGE_DRIVER: GSSC5-25
REVIEW_STATUS: Approved

[REQUIREMENT]
UID: GSSC-PLLR-91
TITLE: Lexical
STATEMENT: >>>
The Section Body SHALL use a normal weight and the black theme token for its text color.
<<<
RATIONALE: >>>
Normal-weight black text keeps body copy readable on the white Container background and distinct from the dark-green header. A fuller type scale is not set yet beyond this weight and token choice.
<<<
DERIVED: True
VERIFICATION_METHOD: Test
CHANGE_DRIVER: GSSC5-25
REVIEW_STATUS: Approved

[[/SECTION]]

[[SECTION]]
UID: GSSC-PLLR-SECTION-RESOURCES
TITLE: Section Resources

[REQUIREMENT]
UID: GSSC-PLLR-92
TITLE: Semantic
STATEMENT: >>>
The Section Resources SHALL present each resource from the Section Contents as a Resource Button when those Contents include resources; selection of a Resource Button SHALL open that resource.
<<<
RATIONALE: >>>
Resources accompany some sections. Equal Resource Buttons that open their targets let the visitor reach related material. This requirement does not set the resource catalog.
<<<
DERIVED: True
VERIFICATION_METHOD: Test
CHANGE_DRIVER: GSSC5-25
REVIEW_STATUS: Approved

[REQUIREMENT]
UID: GSSC-PLLR-93
TITLE: Syntactic
STATEMENT: >>>
The Section Resources SHALL appear below the Section Body inside the Section Container when the Section Contents include resources; SHALL arrange equal-size Resource Buttons in a horizontal strip starting from the left; when that strip overflows the Section width, SHALL present a looping carousel with Resources Prev and Resources Next controls at the ends of the strip, expand the visible Resource Buttons equally to fill the strip width between those controls, slide animation when the strip moves, and movement of the carousel by Left Arrow, Right Arrow, H, and L while a Resource Button is focused; and when that strip fits within the Section width, SHALL show every Resource Button without carousel controls.
<<<
RATIONALE: >>>
A horizontal strip below the body keeps resources grouped after the section text. Overflow uses a looping carousel with end controls and keyboard movement so every resource stays reachable as the Section width changes. Filling the strip between the controls avoids empty space at the end of the visible row without naming a layout framework.
<<<
DERIVED: True
VERIFICATION_METHOD: Test
CHANGE_DRIVER: GSSC5-25
REVIEW_STATUS: Approved

[REQUIREMENT]
UID: GSSC-PLLR-94
TITLE: Lexical
STATEMENT: >>>
The Section Resources strip SHALL present Resource Buttons with shared height using the dark-green theme token for button text and border chrome on the white Container background, and SHALL use the gray theme token for each Resource Button background on hover.
<<<
RATIONALE: >>>
Shared button chrome marks resources as equal controls rather than underline-only links. Gray hover marks each button as activatable. Dark-green tokens keep the strip aligned with the organization palette. A fuller button color role map is not set yet beyond these token choices.
<<<
DERIVED: True
VERIFICATION_METHOD: Test
CHANGE_DRIVER: GSSC5-25
REVIEW_STATUS: Approved

[[SECTION]]
UID: GSSC-PLLR-SECTION-RESOURCE-BUTTON
TITLE: Resource Button

[REQUIREMENT]
UID: GSSC-PLLR-137
TITLE: Semantic
STATEMENT: >>>
The Resource Button SHALL display the resource name from the Section Contents and SHALL open that resource's target when the visitor activates the button.
<<<
RATIONALE: >>>
The button label identifies the resource; activation opens the related material. This requirement does not set the resource catalog.
<<<
DERIVED: True
VERIFICATION_METHOD: Test
CHANGE_DRIVER: GSSC5-25
REVIEW_STATUS: Approved

[REQUIREMENT]
UID: GSSC-PLLR-138
TITLE: Syntactic
STATEMENT: >>>
The Resource Button SHALL occupy one equal-size slot in the Section Resources horizontal strip and SHALL participate in carousel movement when the strip is a carousel.
<<<
RATIONALE: >>>
Equal slots keep buttons aligned in the strip. Carousel participation keeps overflowing resources reachable.
<<<
DERIVED: True
VERIFICATION_METHOD: Test
CHANGE_DRIVER: GSSC5-25
REVIEW_STATUS: Approved

[REQUIREMENT]
UID: GSSC-PLLR-139
TITLE: Lexical
STATEMENT: >>>
The Resource Button SHALL use a shared height with the other Resource Buttons, a normal weight, the dark-green theme token for its text and border, the white theme token for its background, and the gray theme token for its background on hover.
<<<
RATIONALE: >>>
Shared height and dark-green chrome mark each resource as an equal hyperlink button on the white strip. Gray hover marks the control as activatable. A fuller button type scale is not set yet beyond these choices.
<<<
DERIVED: True
VERIFICATION_METHOD: Test
CHANGE_DRIVER: GSSC5-25
REVIEW_STATUS: Approved

[[/SECTION]]

[[SECTION]]
UID: GSSC-PLLR-SECTION-RESOURCES-PREV
TITLE: Resources Prev

[REQUIREMENT]
UID: GSSC-PLLR-140
TITLE: Semantic
STATEMENT: >>>
The Resources Prev control SHALL move the Section Resources carousel one step toward earlier resources when activated, wrapping from the first resource to the last.
<<<
RATIONALE: >>>
Prev steps the looping strip backward so every resource stays reachable from the ends of the strip.
<<<
DERIVED: True
VERIFICATION_METHOD: Test
CHANGE_DRIVER: GSSC5-25
REVIEW_STATUS: Approved

[REQUIREMENT]
UID: GSSC-PLLR-141
TITLE: Syntactic
STATEMENT: >>>
The Resources Prev control SHALL appear at the start of the Section Resources strip when that strip overflows the Section width and is presented as a carousel.
<<<
RATIONALE: >>>
Placing Prev at the start of the strip marks the backward end of the carousel; when the strip fits, Prev is omitted.
<<<
DERIVED: True
VERIFICATION_METHOD: Test
CHANGE_DRIVER: GSSC5-25
REVIEW_STATUS: Approved

[REQUIREMENT]
UID: GSSC-PLLR-142
TITLE: Lexical
STATEMENT: >>>
The Resources Prev control SHALL present a tailless previous-direction arrow icon with no border, rounded corners, the dark-green theme token for its icon color, a transparent background, and the gray theme token for its background on hover.
<<<
RATIONALE: >>>
A borderless rounded icon control matches other public icon buttons. Gray hover marks Prev as activatable without changing the icon color. A fuller control color map is not set yet beyond these token choices.
<<<
DERIVED: True
VERIFICATION_METHOD: Test
CHANGE_DRIVER: GSSC5-25
REVIEW_STATUS: Approved

[[/SECTION]]

[[SECTION]]
UID: GSSC-PLLR-SECTION-RESOURCES-NEXT
TITLE: Resources Next

[REQUIREMENT]
UID: GSSC-PLLR-143
TITLE: Semantic
STATEMENT: >>>
The Resources Next control SHALL move the Section Resources carousel one step toward later resources when activated, wrapping from the last resource to the first.
<<<
RATIONALE: >>>
Next steps the looping strip forward so every resource stays reachable from the ends of the strip.
<<<
DERIVED: True
VERIFICATION_METHOD: Test
CHANGE_DRIVER: GSSC5-25
REVIEW_STATUS: Approved

[REQUIREMENT]
UID: GSSC-PLLR-144
TITLE: Syntactic
STATEMENT: >>>
The Resources Next control SHALL appear at the end of the Section Resources strip when that strip overflows the Section width and is presented as a carousel.
<<<
RATIONALE: >>>
Placing Next at the end of the strip marks the forward end of the carousel; when the strip fits, Next is omitted.
<<<
DERIVED: True
VERIFICATION_METHOD: Test
CHANGE_DRIVER: GSSC5-25
REVIEW_STATUS: Approved

[REQUIREMENT]
UID: GSSC-PLLR-145
TITLE: Lexical
STATEMENT: >>>
The Resources Next control SHALL present a tailless next-direction arrow icon with no border, rounded corners, the dark-green theme token for its icon color, a transparent background, and the gray theme token for its background on hover.
<<<
RATIONALE: >>>
A borderless rounded icon control matches other public icon buttons. Gray hover marks Next as activatable without changing the icon color. A fuller control color map is not set yet beyond these token choices.
<<<
DERIVED: True
VERIFICATION_METHOD: Test
CHANGE_DRIVER: GSSC5-25
REVIEW_STATUS: Approved

[[/SECTION]]

[[/SECTION]]

[[SECTION]]
UID: GSSC-PLLR-SECTION-FROM-CUID
TITLE: Section From CUID

[REQUIREMENT]
UID: GSSC-PLLR-152
TITLE: Semantic
STATEMENT: >>>
The GSSC Website Public Frontend Section From CUID SHALL retrieve a public section's data from the Unified Backend using the section cuid it receives, building Section Contents from that data: the header when that data includes a header, the body, and resources when that data includes resources, using each backend resource string as that resource's name and that resource's target.
<<<
RATIONALE: >>>
Pages identify sections by backend cuid. The loader turns that cuid into Section Contents so the Section Container can place them. Each backend resource string is both the label and the open target until a richer resource schema exists. This requirement does not set which cuids pages pass.
<<<
COMMENT: >>>
Retrieval and Contents construction are one behavior for the cuid input. Resource name and target both come from the same backend string. REVIEW_STATUS stays Changed until owner approval.
<<<
DERIVED: False
VERIFICATION_METHOD: Test
CHANGE_DRIVER: GSSC5-50
REVIEW_STATUS: Changed
RELATIONS:
- TYPE: Parent
  VALUE: GSSC-BHLR-136
  ROLE: Refines

[REQUIREMENT]
UID: GSSC-PLLR-153
TITLE: Syntactic
STATEMENT: >>>
The Section From CUID SHALL place those Section Contents through the Section Container when retrieval succeeds, and omit the Section Container when the Unified Backend does not provide the section for that cuid.
<<<
RATIONALE: >>>
Successful loads reuse the Section Container placement shell. Omitting the Container when the section is unavailable avoids presenting empty chrome. Page assembly chooses where the Section From CUID appears.
<<<
DERIVED: False
VERIFICATION_METHOD: Test
CHANGE_DRIVER: GSSC5-50
REVIEW_STATUS: Changed
RELATIONS:
- TYPE: Parent
  VALUE: GSSC-BHLR-136
  ROLE: Refines

[REQUIREMENT]
UID: GSSC-PLLR-154
TITLE: Lexical
STATEMENT: >>>
The Section From CUID SHALL present the Section Header, Section Body, and Section Resources through the Section Container presentation, without independent lexical chrome of its own.
<<<
RATIONALE: >>>
Chrome, type, and colors stay on the Section Container so the cuid loader does not fork a second section look. Resource carousel and token choices remain those of the Container.
<<<
DERIVED: False
VERIFICATION_METHOD: Test
CHANGE_DRIVER: GSSC5-50
REVIEW_STATUS: Changed
RELATIONS:
- TYPE: Parent
  VALUE: GSSC-BHLR-136
  ROLE: Refines

[[/SECTION]]

[[/SECTION]]

[[SECTION]]
UID: GSSC-PLLR-ERROR
TITLE: Public Error Container

[[SECTION]]
UID: GSSC-PLLR-ERROR-ELEMENT
TITLE: Error Container

[REQUIREMENT]
UID: GSSC-PLLR-95
TITLE: Semantic
STATEMENT: >>>
The Public Frontend Error Container SHALL present Application Error Contents or HTTP Error Contents for the current public error, and present neither when there is no public error.
<<<
RATIONALE: >>>
The Error Container places error Contents on public pages when an error occurs. Application Error Contents and HTTP Error Contents are separate requirements. This requirement does not invent page-specific error copy beyond that container contract.
<<<
DERIVED: False
VERIFICATION_METHOD: Test
CHANGE_DRIVER: GSSC5-24
REVIEW_STATUS: Approved
RELATIONS:
- TYPE: Parent
  VALUE: GSSC-PHLR-48
  ROLE: Refines

[REQUIREMENT]
UID: GSSC-PLLR-96
TITLE: Syntactic
STATEMENT: >>>
The Error Container SHALL appear inside the Page Outlet region of the App Root when it presents error Contents, sit at the bottom-right of that region and size to its Contents up to one quarter of the viewport width and one third of the viewport height at small and above, span the full width of the Page Outlet and limit its height to one third of the viewport below small, keep Report and Dismiss on a chrome banner outside the scrollable Contents region, and scroll only that Contents region vertically when those Contents exceed those size limits.
<<<
RATIONALE: >>>
A compact bottom-right placement keeps the error visible without covering the full page. Width and height caps leave most of the page usable as the viewport resizes. Keeping Report and Dismiss on a non-scrolling banner leaves those actions reachable while long Contents scroll inside the caps.
<<<
DERIVED: False
VERIFICATION_METHOD: Test
CHANGE_DRIVER: GSSC5-24
REVIEW_STATUS: Changed
RELATIONS:
- TYPE: Parent
  VALUE: GSSC-PHLR-48
  ROLE: Refines

[REQUIREMENT]
UID: GSSC-PLLR-97
TITLE: Lexical
STATEMENT: >>>
The Error Container SHALL use the light-red theme token for its background and the dark-red theme token for its border and default text color.
<<<
RATIONALE: >>>
Light-red and dark-red theme tokens mark the Error Container as an error surface in the same family as Prompt field failure chrome. A fuller error color role map is not set yet beyond these token choices.
<<<
DERIVED: False
VERIFICATION_METHOD: Test
CHANGE_DRIVER: GSSC5-24
REVIEW_STATUS: Approved
RELATIONS:
- TYPE: Parent
  VALUE: GSSC-PHLR-48
  ROLE: Refines

[[/SECTION]]

[[SECTION]]
UID: GSSC-PLLR-ERROR-APPLICATION-CONTENTS
TITLE: Application Error Contents

[REQUIREMENT]
UID: GSSC-PLLR-98
TITLE: Semantic
STATEMENT: >>>
When the Error Container presents Application Error Contents, those Contents SHALL display the error name, the error description, and the error reference number, and, when the visitor is a logged-in administrator and debugging information is available, provide that debugging information in a collapsible presentation that starts collapsed.
<<<
RATIONALE: >>>
Application Error Contents tell the visitor which application error occurred and how to refer to it. Collapsed-by-default debugging keeps administrator detail available without crowding the summary. This requirement does not set the name, description, reference format, or debugging payload.
<<<
DERIVED: False
VERIFICATION_METHOD: Test
CHANGE_DRIVER: GSSC5-24
REVIEW_STATUS: Approved
RELATIONS:
- TYPE: Parent
  VALUE: GSSC-PHLR-35
  ROLE: Refines
- TYPE: Parent
  VALUE: GSSC-PHLR-36
  ROLE: Refines
- TYPE: Parent
  VALUE: GSSC-PHLR-37
  ROLE: Refines
- TYPE: Parent
  VALUE: GSSC-PHLR-38
  ROLE: Refines

[REQUIREMENT]
UID: GSSC-PLLR-99
TITLE: Syntactic
STATEMENT: >>>
When the Error Container presents Application Error Contents, the error name, error description, and error reference number SHALL appear in that order inside the Error Container, with the debugging collapsible after those fields when it is available.
<<<
RATIONALE: >>>
Ordering name, description, and reference first keeps the visitor-facing summary readable before optional administrator debugging detail.
<<<
DERIVED: False
VERIFICATION_METHOD: Test
CHANGE_DRIVER: GSSC5-24
REVIEW_STATUS: Approved
RELATIONS:
- TYPE: Parent
  VALUE: GSSC-PHLR-35
  ROLE: Refines
- TYPE: Parent
  VALUE: GSSC-PHLR-36
  ROLE: Refines
- TYPE: Parent
  VALUE: GSSC-PHLR-37
  ROLE: Refines
- TYPE: Parent
  VALUE: GSSC-PHLR-38
  ROLE: Refines

[REQUIREMENT]
UID: GSSC-PLLR-100
TITLE: Lexical
STATEMENT: >>>
When the Error Container presents Application Error Contents, the error name, error description, error reference number, and debugging information SHALL use the dark-red theme token for their text color, with the error name at a semibold weight and the remaining fields at a normal weight.
<<<
RATIONALE: >>>
Semibold dark-red distinguishes the error name on the light-red Error Container. Normal-weight dark-red keeps supporting Application Error fields aligned with the error chrome. A fuller type scale is not set yet beyond these weight and token choices.
<<<
DERIVED: False
VERIFICATION_METHOD: Test
CHANGE_DRIVER: GSSC5-24
REVIEW_STATUS: Approved
RELATIONS:
- TYPE: Parent
  VALUE: GSSC-PHLR-35
  ROLE: Refines
- TYPE: Parent
  VALUE: GSSC-PHLR-36
  ROLE: Refines
- TYPE: Parent
  VALUE: GSSC-PHLR-37
  ROLE: Refines
- TYPE: Parent
  VALUE: GSSC-PHLR-38
  ROLE: Refines

[[/SECTION]]

[[SECTION]]
UID: GSSC-PLLR-ERROR-HTTP-CONTENTS
TITLE: HTTP Error Contents

[REQUIREMENT]
UID: GSSC-PLLR-101
TITLE: Semantic
STATEMENT: >>>
When the Error Container presents HTTP Error Contents, those Contents SHALL display the error code, the error name, and the error description, and, when the visitor is a logged-in administrator and request or response packet information is available, provide each available packet detail in its own collapsible presentation that starts collapsed.
<<<
RATIONALE: >>>
HTTP Error Contents tell the visitor which HTTP failure occurred. Separate collapsed-by-default request and response collapsibles keep administrator packet detail available without crowding the summary. This requirement does not set the code, name, description, or packet payloads.
<<<
DERIVED: False
VERIFICATION_METHOD: Test
CHANGE_DRIVER: GSSC5-24
REVIEW_STATUS: Approved
RELATIONS:
- TYPE: Parent
  VALUE: GSSC-PHLR-39
  ROLE: Refines
- TYPE: Parent
  VALUE: GSSC-PHLR-40
  ROLE: Refines
- TYPE: Parent
  VALUE: GSSC-PHLR-41
  ROLE: Refines
- TYPE: Parent
  VALUE: GSSC-PHLR-42
  ROLE: Refines
- TYPE: Parent
  VALUE: GSSC-PHLR-43
  ROLE: Refines

[REQUIREMENT]
UID: GSSC-PLLR-102
TITLE: Syntactic
STATEMENT: >>>
When the Error Container presents HTTP Error Contents, the error code, error name, and error description SHALL appear in that order inside the Error Container, with the request and response collapsibles after those fields when they are available.
<<<
RATIONALE: >>>
Ordering code, name, and description first keeps the visitor-facing HTTP summary readable before optional administrator packet detail.
<<<
DERIVED: False
VERIFICATION_METHOD: Test
CHANGE_DRIVER: GSSC5-24
REVIEW_STATUS: Approved
RELATIONS:
- TYPE: Parent
  VALUE: GSSC-PHLR-39
  ROLE: Refines
- TYPE: Parent
  VALUE: GSSC-PHLR-40
  ROLE: Refines
- TYPE: Parent
  VALUE: GSSC-PHLR-41
  ROLE: Refines
- TYPE: Parent
  VALUE: GSSC-PHLR-42
  ROLE: Refines
- TYPE: Parent
  VALUE: GSSC-PHLR-43
  ROLE: Refines

[REQUIREMENT]
UID: GSSC-PLLR-103
TITLE: Lexical
STATEMENT: >>>
When the Error Container presents HTTP Error Contents, the error code, error name, error description, request packet information, and response packet information SHALL use the dark-red theme token for their text color, with the error code and error name at a semibold weight and the remaining fields at a normal weight.
<<<
RATIONALE: >>>
Semibold dark-red distinguishes the HTTP status summary on the light-red Error Container. Normal-weight dark-red keeps supporting HTTP Error fields aligned with the error chrome. A fuller type scale is not set yet beyond these weight and token choices.
<<<
DERIVED: False
VERIFICATION_METHOD: Test
CHANGE_DRIVER: GSSC5-24
REVIEW_STATUS: Approved
RELATIONS:
- TYPE: Parent
  VALUE: GSSC-PHLR-39
  ROLE: Refines
- TYPE: Parent
  VALUE: GSSC-PHLR-40
  ROLE: Refines
- TYPE: Parent
  VALUE: GSSC-PHLR-41
  ROLE: Refines
- TYPE: Parent
  VALUE: GSSC-PHLR-42
  ROLE: Refines
- TYPE: Parent
  VALUE: GSSC-PHLR-43
  ROLE: Refines

[[/SECTION]]

[[SECTION]]
UID: GSSC-PLLR-ERROR-DISMISS
TITLE: Dismiss

[REQUIREMENT]
UID: GSSC-PLLR-146
TITLE: Semantic
STATEMENT: >>>
The Error Container Dismiss control SHALL dismiss the Error Container when the visitor activates it.
<<<
RATIONALE: >>>
Dismiss removes the current error presentation so the visitor can continue with the page. Clearing which error is current is a separate service concern.
<<<
DERIVED: False
VERIFICATION_METHOD: Test
CHANGE_DRIVER: GSSC5-24
REVIEW_STATUS: Approved
RELATIONS:
- TYPE: Parent
  VALUE: GSSC-PHLR-48
  ROLE: Refines

[REQUIREMENT]
UID: GSSC-PLLR-147
TITLE: Syntactic
STATEMENT: >>>
The Error Container Dismiss control SHALL appear at the top-right of the Error Container chrome banner outside the scrollable Contents region, with Escape dismissing the Error Container when the Error Container is focused, and with dismiss restoring the focus that was active before the Error Container was presented.
<<<
RATIONALE: >>>
Top-right placement on the non-scrolling chrome banner matches a standard dismiss corner and keeps Dismiss reachable while Contents scroll. Escape when focused and focus restore keep keyboard use predictable without stealing focus from unrelated page controls when the Container is not focused.
<<<
DERIVED: False
VERIFICATION_METHOD: Test
CHANGE_DRIVER: GSSC5-24
REVIEW_STATUS: Changed
RELATIONS:
- TYPE: Parent
  VALUE: GSSC-PHLR-48
  ROLE: Refines

[REQUIREMENT]
UID: GSSC-PLLR-148
TITLE: Lexical
STATEMENT: >>>
The Error Container Dismiss control SHALL present an X mark with a transparent background that becomes the dark-red theme token on hover, rounded corners, and the gray theme token for the X that becomes the white theme token on hover.
<<<
RATIONALE: >>>
Transparent-to-red hover and gray-to-white X mark the control as activatable while staying aligned with the Error Container chrome. A fuller control color map is not set yet beyond these token choices.
<<<
DERIVED: False
VERIFICATION_METHOD: Test
CHANGE_DRIVER: GSSC5-24
REVIEW_STATUS: Approved
RELATIONS:
- TYPE: Parent
  VALUE: GSSC-PHLR-48
  ROLE: Refines

[[/SECTION]]

[[SECTION]]
UID: GSSC-PLLR-ERROR-REPORT
TITLE: Report

[REQUIREMENT]
UID: GSSC-PLLR-149
TITLE: Semantic
STATEMENT: >>>
The Error Container Report control SHALL dismiss the Error Container when the visitor activates it.
<<<
RATIONALE: >>>
Report ends the current error presentation from the visitor side. Sending the error to a backend is a separate feature and is not required here.
<<<
DERIVED: False
VERIFICATION_METHOD: Test
CHANGE_DRIVER: GSSC5-24
REVIEW_STATUS: Approved
RELATIONS:
- TYPE: Parent
  VALUE: GSSC-PHLR-48
  ROLE: Refines

[REQUIREMENT]
UID: GSSC-PLLR-150
TITLE: Syntactic
STATEMENT: >>>
The Error Container Report control SHALL appear at the top-left of the Error Container chrome banner outside the scrollable Contents region, opposite the Dismiss control.
<<<
RATIONALE: >>>
Opposite corners on the non-scrolling chrome banner keep Report and Dismiss reachable without overlapping or scrolling away from the error summary.
<<<
DERIVED: False
VERIFICATION_METHOD: Test
CHANGE_DRIVER: GSSC5-24
REVIEW_STATUS: Changed
RELATIONS:
- TYPE: Parent
  VALUE: GSSC-PHLR-48
  ROLE: Refines

[REQUIREMENT]
UID: GSSC-PLLR-151
TITLE: Lexical
STATEMENT: >>>
The Error Container Report control SHALL use the same Lexical presentation as the Error Container Dismiss control.
<<<
RATIONALE: >>>
Matching Dismiss chrome keeps the two chrome controls visually paired as Error Container actions.
<<<
DERIVED: False
VERIFICATION_METHOD: Test
CHANGE_DRIVER: GSSC5-24
REVIEW_STATUS: Approved
RELATIONS:
- TYPE: Parent
  VALUE: GSSC-PHLR-48
  ROLE: Refines

[[/SECTION]]

[[/SECTION]]

[[SECTION]]
UID: GSSC-PLLR-PROMPT-OVERLAY
TITLE: Public Prompt Overlay

[[SECTION]]
UID: GSSC-PLLR-PROMPT-OVERLAY-ELEMENT
TITLE: Prompt Overlay

[REQUIREMENT]
UID: GSSC-PLLR-107
TITLE: Semantic
STATEMENT: >>>
The Public Prompt Overlay SHALL present the current queued form from the Public Frontend Prompt Overlay service while open, omit its presentation when that queue is empty, advance to the next queued form when the current form completes or submits successfully, cancel the current form when the visitor dismisses it, move focus to the first form control when a form opens, and submit the current form when the visitor presses Enter in a field or activates a form submit control.
<<<
RATIONALE: >>>
No Public Frontend PIR defines a prompt overlay. The overlay is the Container for prompt forms whose Contents the Prompt Overlay service queues. Completing or submitting advances the queue until empty. Dismiss cancels only the current prompt. Focus and Enter submit keep interaction on the form. Contact Overlay remains a separate feature that reuses this overlay. Derived because PIRs do not define this overlay.
<<<
COMMENT: >>>
Form field modules from GSSC5-27. Contact Overlay product UX is GSSC5-31.
<<<
DERIVED: True
VERIFICATION_METHOD: Test
CHANGE_DRIVER: GSSC5-27
REVIEW_STATUS: Approved

[REQUIREMENT]
UID: GSSC-PLLR-108
TITLE: Syntactic
STATEMENT: >>>
The Public Prompt Overlay SHALL cover the viewport with a backdrop while open, center a contents panel over that backdrop, scroll the panel independently of the page, size that panel to the full viewport below the small breakpoint and to at most three-quarters of the viewport width and height at the small breakpoint and above, and keep that panel within the viewport as the page resizes.
<<<
RATIONALE: >>>
Covering and centering focus the visitor on the prompt form. Independent panel scroll keeps the page behind still. Full-screen below small and a three-quarter cap at small and above fit narrow and wide viewports without naming a layout framework.
<<<
COMMENT: >>>
Proposed for owner review (GSSC5-27). Width bands stay implementation-agnostic.
<<<
DERIVED: True
VERIFICATION_METHOD: Test
CHANGE_DRIVER: GSSC5-27
REVIEW_STATUS: Approved

[REQUIREMENT]
UID: GSSC-PLLR-109
TITLE: Lexical
STATEMENT: >>>
The Public Prompt Overlay SHALL use the gray theme token at twenty-five percent opacity for its backdrop, the white theme token for the contents panel background, the dark-green theme token for the panel border and panel text, and the sans-serif theme font.
<<<
RATIONALE: >>>
Theme tokens keep overlay presentation aligned with the organization palette. A fuller color role map for overlays is not set yet beyond these token choices.
<<<
COMMENT: >>>
Proposed for owner review (GSSC5-27). Gray at 25% opacity is the owner-specified backdrop.
<<<
DERIVED: True
VERIFICATION_METHOD: Test
CHANGE_DRIVER: GSSC5-27
REVIEW_STATUS: Approved

[[/SECTION]]

[[SECTION]]
UID: GSSC-PLLR-PROMPT-OVERLAY-DISMISS
TITLE: Dismiss

[REQUIREMENT]
UID: GSSC-PLLR-110
TITLE: Semantic
STATEMENT: >>>
The Prompt Overlay Dismiss control and Escape key SHALL cancel the current prompt when the visitor activates the Dismiss control or presses Escape.
<<<
RATIONALE: >>>
Dismiss and Escape are the cancel paths for the current queued form. Backdrop activation does not cancel. Overlay Contents and field behavior are separate requirements.
<<<
COMMENT: >>>
Proposed for owner review (GSSC5-27). No backdrop dismiss.
<<<
DERIVED: True
VERIFICATION_METHOD: Test
CHANGE_DRIVER: GSSC5-27
REVIEW_STATUS: Approved

[REQUIREMENT]
UID: GSSC-PLLR-111
TITLE: Syntactic
STATEMENT: >>>
The Prompt Overlay Dismiss control SHALL appear at the top-right of the prompt container.
<<<
RATIONALE: >>>
Top-right placement keeps the close path visible without covering the Prompt Form.
<<<
COMMENT: >>>
Proposed for owner review (GSSC5-27).
<<<
DERIVED: True
VERIFICATION_METHOD: Test
CHANGE_DRIVER: GSSC5-27
REVIEW_STATUS: Approved

[REQUIREMENT]
UID: GSSC-PLLR-112
TITLE: Lexical
STATEMENT: >>>
The Prompt Overlay Dismiss control SHALL use the dark-green theme token for its symbol color on a transparent background, rounded corners, the gray theme token for its background on hover, and the sans-serif theme font.
<<<
RATIONALE: >>>
Dark-green on a transparent control keeps Dismiss aligned with panel text. Rounded corners and gray background on hover match other public icon buttons and mark the control as activatable without changing the symbol color. A fuller color role map for overlay controls is not set yet beyond these token choices.
<<<
COMMENT: >>>
Shared icon-button chrome (rounded corners; gray hover) aligned under GSSC5-25.
<<<
DERIVED: True
VERIFICATION_METHOD: Test
CHANGE_DRIVER: >>>
GSSC5-27
GSSC5-25
<<<
REVIEW_STATUS: Approved

[[/SECTION]]

[[SECTION]]
UID: GSSC-PLLR-PROMPT-FORM
TITLE: Prompt Form

[REQUIREMENT]
UID: GSSC-PLLR-113
TITLE: Semantic
STATEMENT: >>>
The Prompt Form SHALL hold the Prompt Overlay field modules the Prompt Overlay service configured for the current prompt.
<<<
RATIONALE: >>>
The form holds the field modules of the current queued prompt. The Prompt Form Title is a separate requirement. Each field module's behavior is a separate requirement.
<<<
COMMENT: >>>
Proposed for owner review (GSSC5-27).
<<<
DERIVED: True
VERIFICATION_METHOD: Test
CHANGE_DRIVER: GSSC5-27
REVIEW_STATUS: Approved

[REQUIREMENT]
UID: GSSC-PLLR-114
TITLE: Syntactic
STATEMENT: >>>
The Prompt Form SHALL arrange its fields in a CSS grid with one column below the small breakpoint and two columns at the small breakpoint and above.
<<<
RATIONALE: >>>
One column on narrow viewports and two columns from small upward keeps field modules readable without naming a layout framework.
<<<
COMMENT: >>>
Proposed for owner review (GSSC5-27).
<<<
DERIVED: True
VERIFICATION_METHOD: Test
CHANGE_DRIVER: GSSC5-27
REVIEW_STATUS: Approved

[REQUIREMENT]
UID: GSSC-PLLR-115
TITLE: Lexical
STATEMENT: >>>
The Prompt Form SHALL inherit the Prompt Overlay font and text color theme tokens.
<<<
RATIONALE: >>>
The form is a layout host for field modules. It inherits overlay type tokens so field chrome stays consistent until each field paints its own presentation.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-FORM-TITLE
TITLE: Title

[REQUIREMENT]
UID: GSSC-PLLR-134
TITLE: Semantic
STATEMENT: >>>
The Prompt Form Title SHALL display the title text the Prompt Overlay service configured for the current prompt.
<<<
RATIONALE: >>>
A configured title names the current prompt so the visitor knows which form is open. The Prompt Overlay service supplies that title with the form Contents.
<<<
COMMENT: >>>
Proposed for owner review (GSSC5-27).
<<<
DERIVED: True
VERIFICATION_METHOD: Test
CHANGE_DRIVER: GSSC5-27
REVIEW_STATUS: Approved

[REQUIREMENT]
UID: GSSC-PLLR-135
TITLE: Syntactic
STATEMENT: >>>
The Prompt Form Title SHALL appear at the start of the prompt container header, opposite the Prompt Overlay Dismiss control.
<<<
RATIONALE: >>>
Placing the title in the header opposite Dismiss gives the title room and keeps Dismiss clear of the form fields.
<<<
COMMENT: >>>
Proposed for owner review (GSSC5-27).
<<<
DERIVED: True
VERIFICATION_METHOD: Test
CHANGE_DRIVER: GSSC5-27
REVIEW_STATUS: Approved

[REQUIREMENT]
UID: GSSC-PLLR-136
TITLE: Lexical
STATEMENT: >>>
The Prompt Form Title SHALL use the sans-serif theme font, a medium font weight, and the dark-green theme token for its text color.
<<<
RATIONALE: >>>
Medium dark-green title text marks the prompt heading without competing with field labels.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-TEXT-FIELD
TITLE: Text

[REQUIREMENT]
UID: GSSC-PLLR-116
TITLE: Semantic
STATEMENT: >>>
The Prompt Overlay Text field SHALL accept visitor text entry with the input type checking the Prompt Overlay service configured for that field, including email checking when configured as email; obscure entered text when configured as a password; present a multiline entry when configured for long content; show its label; start from the default text value when the Prompt Overlay service configures one; and honor enable and disable from that configuration.
<<<
RATIONALE: >>>
Text is the entry field module for free-form and typed values in a prompt form. Type checking, password obscuring, multiline layout, and an optional default value are configuration of that module. Enable and disable gate interaction without removing the field.
<<<
COMMENT: >>>
Default value support added for GSSC5-27.
<<<
DERIVED: True
VERIFICATION_METHOD: Test
CHANGE_DRIVER: GSSC5-27
REVIEW_STATUS: Approved

[REQUIREMENT]
UID: GSSC-PLLR-117
TITLE: Syntactic
STATEMENT: >>>
The Prompt Overlay Text field SHALL place its label on the top border to the left of the entry and participate in the Prompt Form grid.
<<<
RATIONALE: >>>
Entry-style labels sit on the top border so the field remains compact in the form grid.
<<<
COMMENT: >>>
Proposed for owner review (GSSC5-27).
<<<
DERIVED: True
VERIFICATION_METHOD: Test
CHANGE_DRIVER: GSSC5-27
REVIEW_STATUS: Approved

[REQUIREMENT]
UID: GSSC-PLLR-118
TITLE: Lexical
STATEMENT: >>>
The Prompt Overlay Text field SHALL use the dark-green theme token for its border and for an italic label, the white theme token for its fill when enabled and the gray theme token for its fill when disabled, the sans-serif theme font, and the red theme presentation for border, label, and content after failed form validation until the visitor modifies the field.
<<<
RATIONALE: >>>
Shared entry-field chrome keeps Text aligned with other prompt fields. Red after failed validation marks the field until the visitor edits it.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-SELECT-FIELD
TITLE: Select

[REQUIREMENT]
UID: GSSC-PLLR-119
TITLE: Semantic
STATEMENT: >>>
The Prompt Overlay Select field SHALL present a switch that toggles a checked or unchecked choice, show its label, start from the default checked state when the Prompt Overlay service configures one, and honor enable and disable from the Prompt Overlay service configuration.
<<<
RATIONALE: >>>
Select is the switch-styled checkbox module for a prompt form. An optional default checked state seeds the switch when the prompt opens. Enable and disable gate interaction without removing the field.
<<<
COMMENT: >>>
Default value support added for GSSC5-27.
<<<
DERIVED: True
VERIFICATION_METHOD: Test
CHANGE_DRIVER: GSSC5-27
REVIEW_STATUS: Approved

[REQUIREMENT]
UID: GSSC-PLLR-120
TITLE: Syntactic
STATEMENT: >>>
The Prompt Overlay Select field SHALL place its label inside the field border and participate in the Prompt Form grid.
<<<
RATIONALE: >>>
Switch-style labels sit inside the border so the control reads as one unit in the form grid.
<<<
COMMENT: >>>
Proposed for owner review (GSSC5-27).
<<<
DERIVED: True
VERIFICATION_METHOD: Test
CHANGE_DRIVER: GSSC5-27
REVIEW_STATUS: Approved

[REQUIREMENT]
UID: GSSC-PLLR-121
TITLE: Lexical
STATEMENT: >>>
The Prompt Overlay Select field SHALL use the dark-green theme token for its border and for a normal-weight label, the white theme token for its fill when enabled and the gray theme token for its fill when disabled, the sans-serif theme font, and the red theme presentation for border, label, and content after failed form validation until the visitor modifies the field.
<<<
RATIONALE: >>>
Shared switch-field chrome keeps Select aligned with other prompt fields. Normal-weight labels distinguish switch fields from italic entry labels.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-OPTIONS-FIELD
TITLE: Options

[REQUIREMENT]
UID: GSSC-PLLR-122
TITLE: Semantic
STATEMENT: >>>
The Prompt Overlay Options field SHALL present mutually exclusive choices as radio options, show a label for the field and for each choice, start from the default choice when the Prompt Overlay service configures one, and honor enable and disable from the Prompt Overlay service configuration.
<<<
RATIONALE: >>>
Options is the radio-group module for a prompt form. Mutually exclusive choices keep a single selection. An optional default choice seeds the group when the prompt opens. Enable and disable gate interaction without removing the field.
<<<
COMMENT: >>>
Default value support added for GSSC5-27.
<<<
DERIVED: True
VERIFICATION_METHOD: Test
CHANGE_DRIVER: GSSC5-27
REVIEW_STATUS: Approved

[REQUIREMENT]
UID: GSSC-PLLR-123
TITLE: Syntactic
STATEMENT: >>>
The Prompt Overlay Options field SHALL place its field label on the top border to the left, arrange choice labels with their radio controls, and participate in the Prompt Form grid.
<<<
RATIONALE: >>>
Entry-style field labels and inline choice labels keep Options readable in the form grid.
<<<
COMMENT: >>>
Proposed for owner review (GSSC5-27).
<<<
DERIVED: True
VERIFICATION_METHOD: Test
CHANGE_DRIVER: GSSC5-27
REVIEW_STATUS: Approved

[REQUIREMENT]
UID: GSSC-PLLR-124
TITLE: Lexical
STATEMENT: >>>
The Prompt Overlay Options field SHALL use the dark-green theme token for its border and for an italic field label, the white theme token for its fill when enabled and the gray theme token for its fill when disabled, the sans-serif theme font, and the red theme presentation for border, label, and content after failed form validation until the visitor modifies the field.
<<<
RATIONALE: >>>
Shared entry-style chrome keeps Options aligned with other labeled prompt fields. Red after failed validation marks the field until the visitor edits it.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-BUTTON-FIELD
TITLE: Button

[REQUIREMENT]
UID: GSSC-PLLR-125
TITLE: Semantic
STATEMENT: >>>
The Prompt Overlay Button field SHALL present an activatable control within the Prompt Form, perform the submit role when the Prompt Overlay service configures it as a submit control, show its label, and honor enable and disable from that configuration.
<<<
RATIONALE: >>>
Button is the activatable control module for a prompt form, including submit when configured. Enable and disable gate interaction without removing the control.
<<<
COMMENT: >>>
Proposed for owner review (GSSC5-27).
<<<
DERIVED: True
VERIFICATION_METHOD: Test
CHANGE_DRIVER: GSSC5-27
REVIEW_STATUS: Approved

[REQUIREMENT]
UID: GSSC-PLLR-126
TITLE: Syntactic
STATEMENT: >>>
The Prompt Overlay Button field SHALL place its label inside the control and participate in the Prompt Form grid.
<<<
RATIONALE: >>>
An in-control label keeps the Button a single activatable unit in the form grid.
<<<
COMMENT: >>>
Proposed for owner review (GSSC5-27).
<<<
DERIVED: True
VERIFICATION_METHOD: Test
CHANGE_DRIVER: GSSC5-27
REVIEW_STATUS: Approved

[REQUIREMENT]
UID: GSSC-PLLR-127
TITLE: Lexical
STATEMENT: >>>
The Prompt Overlay Button field SHALL use the dark-green theme token for its border and for a normal-weight label, the white theme token for its fill when enabled and the gray theme token for its fill when disabled or hovered, the sans-serif theme font, and the red theme presentation for border, label, and content after failed form validation until the visitor modifies the field.
<<<
RATIONALE: >>>
Shared control chrome keeps Button aligned with other prompt fields. Gray on hover marks the control as activatable. Red after failed validation marks the control until the visitor interacts again when validation applies.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-FILE-FIELD
TITLE: File

[REQUIREMENT]
UID: GSSC-PLLR-128
TITLE: Semantic
STATEMENT: >>>
The Prompt Overlay File field SHALL let the visitor pick a file, show its label, start from the default file when the Prompt Overlay service configures one, and honor enable and disable from the Prompt Overlay service configuration.
<<<
RATIONALE: >>>
File is the file-pick module for a prompt form. An optional default file seeds the field when the prompt opens. Enable and disable gate interaction without removing the field.
<<<
COMMENT: >>>
Default value support added for GSSC5-27.
<<<
DERIVED: True
VERIFICATION_METHOD: Test
CHANGE_DRIVER: GSSC5-27
REVIEW_STATUS: Approved

[REQUIREMENT]
UID: GSSC-PLLR-129
TITLE: Syntactic
STATEMENT: >>>
The Prompt Overlay File field SHALL place its label on the top border to the left of the file control and participate in the Prompt Form grid.
<<<
RATIONALE: >>>
Entry-style labels sit on the top border so the File field remains compact in the form grid.
<<<
COMMENT: >>>
Proposed for owner review (GSSC5-27).
<<<
DERIVED: True
VERIFICATION_METHOD: Test
CHANGE_DRIVER: GSSC5-27
REVIEW_STATUS: Approved

[REQUIREMENT]
UID: GSSC-PLLR-130
TITLE: Lexical
STATEMENT: >>>
The Prompt Overlay File field SHALL use the dark-green theme token for its border and for an italic label, the white theme token for its fill when enabled and the gray theme token for its fill when disabled, the sans-serif theme font, and the red theme presentation for border, label, and content after failed form validation until the visitor modifies the field.
<<<
RATIONALE: >>>
Shared entry-field chrome keeps File aligned with other prompt fields. Red after failed validation marks the field until the visitor edits it.
<<<
COMMENT: >>>
Proposed for owner review (GSSC5-27).
<<<
DERIVED: True
VERIFICATION_METHOD: Test
CHANGE_DRIVER: GSSC5-27
REVIEW_STATUS: Approved

[[/SECTION]]

[[SECTION]]
UID: GSSC-PLLR-PROMPT-OPTIONS-LIST-FIELD
TITLE: Options List

[REQUIREMENT]
UID: GSSC-PLLR-131
TITLE: Semantic
STATEMENT: >>>
The Prompt Overlay Options List field SHALL let the visitor choose one value from a configured list, show its label, start from the default choice when the Prompt Overlay service configures one, and honor enable and disable from the Prompt Overlay service configuration.
<<<
RATIONALE: >>>
Options List is the dropdown choose-one module for a prompt form. An optional default choice seeds the list when the prompt opens. Enable and disable gate interaction without removing the field.
<<<
COMMENT: >>>
Default value support added for GSSC5-27.
<<<
DERIVED: True
VERIFICATION_METHOD: Test
CHANGE_DRIVER: GSSC5-27
REVIEW_STATUS: Approved

[REQUIREMENT]
UID: GSSC-PLLR-132
TITLE: Syntactic
STATEMENT: >>>
The Prompt Overlay Options List field SHALL place its label on the top border to the left of the list control and participate in the Prompt Form grid.
<<<
RATIONALE: >>>
Entry-style labels sit on the top border so the Options List field remains compact in the form grid.
<<<
COMMENT: >>>
Proposed for owner review (GSSC5-27).
<<<
DERIVED: True
VERIFICATION_METHOD: Test
CHANGE_DRIVER: GSSC5-27
REVIEW_STATUS: Approved

[REQUIREMENT]
UID: GSSC-PLLR-133
TITLE: Lexical
STATEMENT: >>>
The Prompt Overlay Options List field SHALL use the dark-green theme token for its border and for an italic label, the white theme token for its fill when enabled and the gray theme token for its fill when disabled, the sans-serif theme font, and the red theme presentation for border, label, and content after failed form validation until the visitor modifies the field.
<<<
RATIONALE: >>>
Shared entry-field chrome keeps Options List aligned with other prompt fields. Red after failed validation marks the field until the visitor edits it.
<<<
COMMENT: >>>
Proposed for owner review (GSSC5-27).
<<<
DERIVED: True
VERIFICATION_METHOD: Test
CHANGE_DRIVER: GSSC5-27
REVIEW_STATUS: Approved

[[/SECTION]]

[[/SECTION]]

[[SECTION]]
UID: GSSC-PLLR-CONTACT-OVERLAY
TITLE: Public Contact Overlay

[REQUIREMENT]
UID: GSSC-PLLR-155
TITLE: Open
STATEMENT: >>>
The Public Contact Overlay SHALL enqueue its contact form on the Public Frontend Prompt Overlay when a visitor opens it.
<<<
RATIONALE: >>>
No Public Frontend PIR defines a contact overlay. Header Contact and Footer Contact open this overlay so a visitor can draft a message to the organization. Queueing the form on the Prompt Overlay reuses that shell. Phone number, email address, and postal address stay on the Footer. Derived because PIRs do not define this overlay.
<<<
COMMENT: >>>
Proposed for owner review (GSSC5-31). Promotes the prior software-only contact form PoC. No send or mail API is in scope.
<<<
DERIVED: True
VERIFICATION_METHOD: Test
CHANGE_DRIVER: GSSC5-31
REVIEW_STATUS: Changed

[[SECTION]]
UID: GSSC-PLLR-CONTACT-FORM
TITLE: Contact Form

[REQUIREMENT]
UID: GSSC-PLLR-156
TITLE: Semantic
STATEMENT: >>>
The Public Contact Overlay form SHALL collect the visitor's name, email address, contact reason, and message for a draft message to the organization, require each of those inputs before accepting submit, start the contact reason at General Inquiry, fill the name and email from the Public Frontend Member Session when a member is signed in, and complete the draft when the visitor submits a valid form.
<<<
RATIONALE: >>>
The form is the draft Contents for a message to the organization. Required inputs keep an incomplete draft from completing. General Inquiry is the default contact reason. Signed-in name and email come from the Member Session so a member does not retype known identity. Completing the draft ends the current Contact Overlay form without a send or mail API.
<<<
COMMENT: >>>
Owner feedback (GSSC5-31): default General Inquiry; autofill Name and Email when signed in. Field module chrome is owned by Prompt Overlay requirements.
<<<
DERIVED: True
VERIFICATION_METHOD: Test
CHANGE_DRIVER: >>>
GSSC5-31
<<<
REVIEW_STATUS: Changed

[REQUIREMENT]
UID: GSSC-PLLR-157
TITLE: Syntactic
STATEMENT: >>>
The Public Contact Overlay form SHALL appear as the current Prompt Overlay form when the Public Contact Overlay is open.
<<<
RATIONALE: >>>
Presenting the contact form through the Prompt Overlay keeps Contact Overlay Contents in the shared prompt shell without a separate overlay container.
<<<
COMMENT: >>>
Proposed for owner review (GSSC5-31). Overlay chrome sizing and dismiss remain Prompt Overlay requirements.
<<<
DERIVED: True
VERIFICATION_METHOD: Test
CHANGE_DRIVER: GSSC5-31
REVIEW_STATUS: Changed

[REQUIREMENT]
UID: GSSC-PLLR-158
TITLE: Lexical
STATEMENT: >>>
The Public Contact Overlay form SHALL use the title Contact; the field labels Name, Email, Contact reason, and Message; the contact reason choices General Inquiry, Membership, Research Help, Website Issue, and Other; the submit control label Submit; and the Prompt Overlay text, options-list, and button field modules for those fields.
<<<
RATIONALE: >>>
Those labels and choices define the Contact Overlay draft wording. Each contact reason option capitalizes every word. Reusing Prompt Overlay field modules keeps Contact Overlay presentation aligned with other prompt forms. Field module Lexical detail remains under Prompt Overlay requirements.
<<<
COMMENT: >>>
Owner feedback (GSSC5-31): title-case reason options; add Website Issue.
<<<
DERIVED: True
VERIFICATION_METHOD: Test
CHANGE_DRIVER: >>>
GSSC5-31
<<<
REVIEW_STATUS: Changed

[[/SECTION]]

[[/SECTION]]

[[/SECTION]]

[[SECTION]]
UID: GSSC-PLLR-PUBLIC-PAGES
TITLE: Public Pages

[[SECTION]]
UID: GSSC-PLLR-RESEARCH-TOOLS-PAGE
TITLE: Research Tools Page

[[SECTION]]
UID: GSSC-PLLR-SOCIETY-RESOURCES-TOOLS-LIST
TITLE: Society Resources and Tools List

[REQUIREMENT]
UID: GSSC-PLLR-159
TITLE: Semantic
STATEMENT: >>>
The Society Resources and Tools List SHALL request the current research tools from the Unified Backend research tools list as normal research tools page content, identifying each listed tool by that tool's cuid, title, and reference link in the order the Unified Backend provides.
<<<
RATIONALE: >>>
The research tools page lists society-recommended tools such as charts, instruction sheets, and outside resource links from the dedicated research-tools catalog. That catalog is normal webpage content for this page, not generic section Contents. Cemetery Project pages are outside this list. Tagged generic sections and Section From CUID are not the source for this list.
<<<
COMMENT: >>>
REVIEW_STATUS stays Changed until owner approval. Owner clarified the tools listing lives in normal page content, not under generic/Section-from-CUID trees.
<<<
DERIVED: False
VERIFICATION_METHOD: Test
CHANGE_DRIVER: GSSC5-18
REVIEW_STATUS: Changed
RELATIONS:
- TYPE: Parent
  VALUE: GSSC-PHLR-83
  ROLE: Refines

[REQUIREMENT]
UID: GSSC-PLLR-160
TITLE: Syntactic
STATEMENT: >>>
The Society Resources and Tools List SHALL place the Research Resources heading and each listed tool as a Research Tool Link in a hyperlink grid in the research tools page's normal webpage content, not nested inside a generic section, omitting the grid when the Unified Backend provides no tools.
<<<
RATIONALE: >>>
Legacy research tools used a heading and multi-column link layout hosted as page content. The tools subsection is a peer of normal page chrome/content, not a child of the Section Container or Section From CUID. An empty or unavailable catalog leaves the page without the grid. Cemetery Project pages remain outside this placement.
<<<
DERIVED: False
VERIFICATION_METHOD: Test
CHANGE_DRIVER: GSSC5-18
REVIEW_STATUS: Changed
RELATIONS:
- TYPE: Parent
  VALUE: GSSC-PHLR-83
  ROLE: Refines

[REQUIREMENT]
UID: GSSC-PLLR-161
TITLE: Lexical
STATEMENT: >>>
The Society Resources and Tools List SHALL use the public white outermost surface and sans-serif default on the page host, present the Research Resources heading in dark green, and arrange Research Tool Links in a multi-column centered grid that becomes a single column when the page is narrow.
<<<
RATIONALE: >>>
The layout refines the legacy research tools grid with public theme tokens. Heading and host chrome stay on the list; each link's own type color is a separate requirement.
<<<
DERIVED: False
VERIFICATION_METHOD: Test
CHANGE_DRIVER: GSSC5-18
REVIEW_STATUS: Changed
RELATIONS:
- TYPE: Parent
  VALUE: GSSC-PHLR-83
  ROLE: Refines

[[/SECTION]]

[[SECTION]]
UID: GSSC-PLLR-RESEARCH-TOOL-LINK
TITLE: Research Tool Link

[REQUIREMENT]
UID: GSSC-PLLR-228
TITLE: Semantic
STATEMENT: >>>
A Research Tool Link SHALL present that tool's title and open that tool's reference link when selected.
<<<
RATIONALE: >>>
Each catalog entry is a titled hyperlink to the tool's reference. The list supplies title and reference link from the Unified Backend.
<<<
DERIVED: False
VERIFICATION_METHOD: Test
CHANGE_DRIVER: GSSC5-18
REVIEW_STATUS: Changed
RELATIONS:
- TYPE: Parent
  VALUE: GSSC-PHLR-83
  ROLE: Refines

[REQUIREMENT]
UID: GSSC-PLLR-229
TITLE: Syntactic
STATEMENT: >>>
A Research Tool Link SHALL occupy one cell in the Society Resources and Tools List hyperlink grid in normal research tools page content.
<<<
RATIONALE: >>>
Grid cells carry one tool each so the list reads as a resource grid on the page, not as Contents nested under a generic section.
<<<
DERIVED: False
VERIFICATION_METHOD: Test
CHANGE_DRIVER: GSSC5-18
REVIEW_STATUS: Changed
RELATIONS:
- TYPE: Parent
  VALUE: GSSC-PHLR-83
  ROLE: Refines

[REQUIREMENT]
UID: GSSC-PLLR-230
TITLE: Lexical
STATEMENT: >>>
A Research Tool Link SHALL use sans-serif type in the public dark green theme color.
<<<
RATIONALE: >>>
Link color and typeface match the public palette so research tools read as primary navigational links on a white host.
<<<
DERIVED: False
VERIFICATION_METHOD: Test
CHANGE_DRIVER: GSSC5-18
REVIEW_STATUS: Changed
RELATIONS:
- TYPE: Parent
  VALUE: GSSC-PHLR-83
  ROLE: Refines

[[/SECTION]]

[[/SECTION]]

[[SECTION]]
UID: GSSC-PLLR-PUBLICATIONS-PAGE
TITLE: Publications Page

[[SECTION]]
UID: GSSC-PLLR-SOCIETY-PUBLICATIONS-LIST
TITLE: Society Publications List

[REQUIREMENT]
UID: GSSC-PLLR-243
TITLE: Semantic
STATEMENT: >>>
The Society Publications List SHALL request the current society publications from the Unified Backend publications list as normal publications page content, identifying each listed publication by that publication's cuid, title, reference link, and description in the order the Unified Backend provides.
<<<
RATIONALE: >>>
The publications page lists society publications from the dedicated publications catalog as normal webpage content, not generic section Contents. The Stanislaus County Cemetery Project and War Veterans of Stanislaus County are outside this list. Tagged generic sections and Section From CUID are not the source for this list.
<<<
COMMENT: >>>
Mirrors the Research Tools page pattern with optional description under each title. Publication Link refines Society Publications List (GSSC-PHLR-84); reference links supersede dedicated-page listing (GSSC-PHLR-85) for this catalog.
<<<
DERIVED: False
VERIFICATION_METHOD: Test
CHANGE_DRIVER: GSSC5-19
REVIEW_STATUS: Approved
RELATIONS:
- TYPE: Parent
  VALUE: GSSC-PHLR-84
  ROLE: Refines

[REQUIREMENT]
UID: GSSC-PLLR-244
TITLE: Syntactic
STATEMENT: >>>
The Society Publications List SHALL place the Publications heading and each listed publication as a Publication Link with that publication's Publication Description when present in a hyperlink grid in the publications page's normal webpage content, not nested inside a generic section, omitting the grid when the Unified Backend provides no publications.
<<<
RATIONALE: >>>
Legacy publications used a titled link layout hosted as page content. The publications subsection is a peer of normal page chrome/content, not a child of the Section Container or Section From CUID. An empty or unavailable catalog leaves the page without the grid. Cemetery Project and War Veterans remain outside this placement.
<<<
DERIVED: False
VERIFICATION_METHOD: Test
CHANGE_DRIVER: GSSC5-19
REVIEW_STATUS: Approved
RELATIONS:
- TYPE: Parent
  VALUE: GSSC-PHLR-84
  ROLE: Refines

[REQUIREMENT]
UID: GSSC-PLLR-245
TITLE: Lexical
STATEMENT: >>>
The Society Publications List SHALL use the public white outermost surface and sans-serif default on the page host, present the Publications heading in dark green, and arrange Publication Links in a multi-column centered grid that becomes a single column when the page is narrow.
<<<
RATIONALE: >>>
The layout refines the legacy publications grid with public theme tokens, matching the Research Tools page host treatment. Heading and host chrome stay on the list; each link and description's own type color is a separate requirement.
<<<
DERIVED: False
VERIFICATION_METHOD: Test
CHANGE_DRIVER: GSSC5-19
REVIEW_STATUS: Approved
RELATIONS:
- TYPE: Parent
  VALUE: GSSC-PHLR-84
  ROLE: Refines

[[/SECTION]]

[[SECTION]]
UID: GSSC-PLLR-PUBLICATION-LINK
TITLE: Publication Link

[REQUIREMENT]
UID: GSSC-PLLR-246
TITLE: Semantic
STATEMENT: >>>
A Publication Link SHALL present that publication's title and open that publication's reference link when selected.
<<<
RATIONALE: >>>
Each catalog entry is a titled hyperlink to the publication's reference. The list supplies title and reference link from the Unified Backend.
<<<
DERIVED: False
VERIFICATION_METHOD: Test
CHANGE_DRIVER: GSSC5-19
REVIEW_STATUS: Approved
RELATIONS:
- TYPE: Parent
  VALUE: GSSC-PHLR-84
  ROLE: Refines

[REQUIREMENT]
UID: GSSC-PLLR-247
TITLE: Syntactic
STATEMENT: >>>
A Publication Link SHALL occupy the title position in one cell of the Society Publications List hyperlink grid in normal publications page content, above that cell's Publication Description when a description is present.
<<<
RATIONALE: >>>
Grid cells carry one publication each so the list reads as a resource grid on the page, not as Contents nested under a generic section. The title link leads; optional description follows below.
<<<
DERIVED: False
VERIFICATION_METHOD: Test
CHANGE_DRIVER: GSSC5-19
REVIEW_STATUS: Approved
RELATIONS:
- TYPE: Parent
  VALUE: GSSC-PHLR-84
  ROLE: Refines

[REQUIREMENT]
UID: GSSC-PLLR-248
TITLE: Lexical
STATEMENT: >>>
A Publication Link SHALL use sans-serif type in the public dark green theme color.
<<<
RATIONALE: >>>
Link color and typeface match the public palette so publications read as primary navigational links on a white host.
<<<
DERIVED: False
VERIFICATION_METHOD: Test
CHANGE_DRIVER: GSSC5-19
REVIEW_STATUS: Approved
RELATIONS:
- TYPE: Parent
  VALUE: GSSC-PHLR-84
  ROLE: Refines

[[/SECTION]]

[[SECTION]]
UID: GSSC-PLLR-PUBLICATION-DESCRIPTION
TITLE: Publication Description

[REQUIREMENT]
UID: GSSC-PLLR-249
TITLE: Semantic
STATEMENT: >>>
A Publication Description SHALL display that publication's description text from the Unified Backend when that publication has a description, and SHALL be omitted when that publication has no description.
<<<
RATIONALE: >>>
Optional description text accompanies a publication listing when the catalog provides it. Absent descriptions leave the cell with only the title link.
<<<
DERIVED: False
VERIFICATION_METHOD: Test
CHANGE_DRIVER: GSSC5-19
REVIEW_STATUS: Approved
RELATIONS:
- TYPE: Parent
  VALUE: GSSC-PHLR-84
  ROLE: Refines

[REQUIREMENT]
UID: GSSC-PLLR-250
TITLE: Syntactic
STATEMENT: >>>
A Publication Description SHALL appear below the Publication Link in the same Society Publications List grid cell when that publication has a description.
<<<
RATIONALE: >>>
Placing description under the title keeps the link primary and the supporting text secondary within the cell.
<<<
DERIVED: False
VERIFICATION_METHOD: Test
CHANGE_DRIVER: GSSC5-19
REVIEW_STATUS: Approved
RELATIONS:
- TYPE: Parent
  VALUE: GSSC-PHLR-84
  ROLE: Refines

[REQUIREMENT]
UID: GSSC-PLLR-251
TITLE: Lexical
STATEMENT: >>>
A Publication Description SHALL use sans-serif type, normal weight, and the public black theme color at a base text size.
<<<
RATIONALE: >>>
Normal black body text under the dark-green title link keeps optional descriptions readable without competing with the link.
<<<
DERIVED: False
VERIFICATION_METHOD: Test
CHANGE_DRIVER: GSSC5-19
REVIEW_STATUS: Approved
RELATIONS:
- TYPE: Parent
  VALUE: GSSC-PHLR-84
  ROLE: Refines

[[/SECTION]]

[[/SECTION]]

[[/SECTION]]

[[SECTION]]
UID: GSSC-PLLR-SERVICES
TITLE: Public Services

[[SECTION]]
UID: GSSC-PLLR-KV-STORE
TITLE: Key-Value Store

[REQUIREMENT]
UID: GSSC-PLLR-76
TITLE: Key-Value Retrieval
STATEMENT: >>>
The Public Frontend Key-Value Store SHALL retrieve the value for a requested key from the Unified Backend key-value store.
<<<
RATIONALE: >>>
Global website data lives in the Unified Backend key-value store. The Public Frontend Key-Value Store fetches that value so other Public Frontend services can use it.
<<<
DERIVED: False
VERIFICATION_METHOD: Test
CHANGE_DRIVER: GSSC5-23
REVIEW_STATUS: Approved
RELATIONS:
- TYPE: Parent
  VALUE: GSSC-BHLR-119
  ROLE: Refines

[REQUIREMENT]
UID: GSSC-PLLR-77
TITLE: Key-Value Absence
STATEMENT: >>>
When the Unified Backend key-value store has no entry for the requested key, the Public Frontend Key-Value Store SHALL provide no value.
<<<
RATIONALE: >>>
A missing key is not an error for the public shell. Callers treat the absent value as empty until the store has an entry.
<<<
DERIVED: False
VERIFICATION_METHOD: Test
CHANGE_DRIVER: GSSC5-23
REVIEW_STATUS: Approved
RELATIONS:
- TYPE: Parent
  VALUE: GSSC-BHLR-119
  ROLE: Refines

[[/SECTION]]

[[SECTION]]
UID: GSSC-PLLR-SOCIETY-CONTACT
TITLE: Society Contact

[REQUIREMENT]
UID: GSSC-PLLR-78
TITLE: Society Phone Number
STATEMENT: >>>
The Public Frontend Society Contact service SHALL provide the society's phone number from the Key-Value Store under the key society.phoneNumber.
<<<
RATIONALE: >>>
Footer Phone Number reads the number from this service. The Key-Value Store key society.phoneNumber holds that number. This requirement does not set the current number.
<<<
DERIVED: False
VERIFICATION_METHOD: Test
CHANGE_DRIVER: GSSC5-23
REVIEW_STATUS: Approved
RELATIONS:
- TYPE: Parent
  VALUE: GSSC-PHLR-24
  ROLE: Refines

[REQUIREMENT]
UID: GSSC-PLLR-79
TITLE: Society Email Address
STATEMENT: >>>
The Public Frontend Society Contact service SHALL provide the society's email address from the Key-Value Store under the key society.emailAddress.
<<<
RATIONALE: >>>
Footer Email Address reads the address from this service. The Key-Value Store key society.emailAddress holds that address. This requirement does not set the current address.
<<<
DERIVED: False
VERIFICATION_METHOD: Test
CHANGE_DRIVER: GSSC5-23
REVIEW_STATUS: Approved
RELATIONS:
- TYPE: Parent
  VALUE: GSSC-PHLR-25
  ROLE: Refines

[REQUIREMENT]
UID: GSSC-PLLR-80
TITLE: Society Postal Address
STATEMENT: >>>
The Public Frontend Society Contact service SHALL provide the society's postal address from the Key-Value Store under the key society.postalAddress.
<<<
RATIONALE: >>>
Footer Postal Address reads the address from this service. The Key-Value Store key society.postalAddress holds that address. This requirement does not set the current address.
<<<
DERIVED: False
VERIFICATION_METHOD: Test
CHANGE_DRIVER: GSSC5-23
REVIEW_STATUS: Approved
RELATIONS:
- TYPE: Parent
  VALUE: GSSC-PHLR-26
  ROLE: Refines

[REQUIREMENT]
UID: GSSC-PLLR-81
TITLE: Society Organization Name
STATEMENT: >>>
The Public Frontend Society Contact service SHALL provide the society's organization name from the Key-Value Store under the key society.organizationName.
<<<
RATIONALE: >>>
Footer Organization Name reads the full name from this service. The Key-Value Store key society.organizationName holds that name. This requirement does not set the current name.
<<<
DERIVED: False
VERIFICATION_METHOD: Test
CHANGE_DRIVER: GSSC5-23
REVIEW_STATUS: Approved
RELATIONS:
- TYPE: Parent
  VALUE: GSSC-PHLR-21
  ROLE: Refines

[REQUIREMENT]
UID: GSSC-PLLR-82
TITLE: Society Organization Acronym
STATEMENT: >>>
The Public Frontend Society Contact service SHALL provide the society's organization acronym from the Key-Value Store under the key society.organizationAcronym.
<<<
RATIONALE: >>>
Footer Organization Name reads the acronym from this service for narrow presentations. The Key-Value Store key society.organizationAcronym holds that acronym. This requirement does not set the current acronym.
<<<
DERIVED: False
VERIFICATION_METHOD: Test
CHANGE_DRIVER: GSSC5-23
REVIEW_STATUS: Approved
RELATIONS:
- TYPE: Parent
  VALUE: GSSC-PHLR-21
  ROLE: Refines

[[/SECTION]]

[[/SECTION]]

[[SECTION]]
UID: GSSC-PLLR-LEADERSHIP-PAGE
TITLE: Public Leadership Page

[[SECTION]]
UID: GSSC-PLLR-LEADERSHIP-INTRO
TITLE: Leadership Intro

[REQUIREMENT]
UID: GSSC-PLLR-234
TITLE: Semantic
STATEMENT: >>>
The Leadership Intro SHALL retrieve the public leadership intro sections from the Unified Backend and place each retrieved section through the Section From CUID.
<<<
RATIONALE: >>>
Intro wording lives in backend sections so editors can change it without a code change. Section From CUID places each section through the Section Container. Derived because no Public Frontend PIR names a leadership intro block.
<<<
COMMENT: >>>
GSSC5-16. SW binds the leadership intro tag; requirements stay tag-agnostic.
<<<
DERIVED: True
VERIFICATION_METHOD: Test
CHANGE_DRIVER: GSSC5-16
REVIEW_STATUS: Approved

[REQUIREMENT]
UID: GSSC-PLLR-235
TITLE: Syntactic
STATEMENT: >>>
The Leadership Intro SHALL appear at the top of the public leadership page above Officers, place each intro section through the Section From CUID in backend index order, and omit the Intro when the Unified Backend provides no leadership intro sections.
<<<
RATIONALE: >>>
Intro precedes the roster so visitors see page context first. Index order preserves the backend section sequence. Omitting an empty Intro avoids blank chrome.
<<<
DERIVED: True
VERIFICATION_METHOD: Test
CHANGE_DRIVER: GSSC5-16
REVIEW_STATUS: Approved

[REQUIREMENT]
UID: GSSC-PLLR-236
TITLE: Lexical
STATEMENT: >>>
The Leadership Intro SHALL present its Section Header, Section Body, and Section Resources through the Section From CUID presentation, without independent lexical chrome of its own.
<<<
RATIONALE: >>>
Intro reuses Section From CUID so leadership sections share the Section Container look with other public sections.
<<<
DERIVED: True
VERIFICATION_METHOD: Test
CHANGE_DRIVER: GSSC5-16
REVIEW_STATUS: Approved

[[/SECTION]]

[[SECTION]]
UID: GSSC-PLLR-OFFICERS
TITLE: Officers

[REQUIREMENT]
UID: GSSC-PLLR-162
TITLE: Semantic
STATEMENT: >>>
The Officers SHALL retrieve the Unified Backend leadership list, present each officer office with the name of the leader whose Position matches that office when that list includes such a leader with a name, present that leader's preferred contact for contact when the matched entry includes the preferred contact value, present that leader's Account Photo when the matched entry includes Account Photo, and present Vacant when that list has no matching Position or the matching leader has no name.
<<<
RATIONALE: >>>
The leadership list supplies current officer names. Matching by Position fills each officer slot. Preferred contact and Account Photo come from the list entry when present. Vacant marks an empty slot because the list omits empty Position.
<<<
COMMENT: >>>
Canonical officer titles are Lexical. Card chrome is Contact Card Large.
<<<
DERIVED: False
VERIFICATION_METHOD: Test
CHANGE_DRIVER: GSSC5-16
REVIEW_STATUS: Approved
RELATIONS:
- TYPE: Parent
  VALUE: GSSC-PHLR-76
  ROLE: Refines
- TYPE: Parent
  VALUE: GSSC-PHLR-78
  ROLE: Refines
- TYPE: Parent
  VALUE: GSSC-PHLR-79
  ROLE: Refines

[REQUIREMENT]
UID: GSSC-PLLR-163
TITLE: Syntactic
STATEMENT: >>>
The Officers SHALL appear on the public leadership page below the Leadership Intro and above the Directors at Large as a grid of large contact cards with at most three columns, resizing with the page width.
<<<
RATIONALE: >>>
A three-column large-card grid keeps the six officer offices scannable. Placement between Intro and Directors matches the page order. Resizing with page width keeps the grid usable on narrow and wide layouts.
<<<
DERIVED: False
VERIFICATION_METHOD: Test
CHANGE_DRIVER: GSSC5-16
REVIEW_STATUS: Approved
RELATIONS:
- TYPE: Parent
  VALUE: GSSC-PHLR-76
  ROLE: Refines

[REQUIREMENT]
UID: GSSC-PLLR-164
TITLE: Lexical
STATEMENT: >>>
The Officers SHALL use the section title Officers; the office titles President, 1st Vice President, 2nd Vice President, Secretary, Treasurer, and Past President; the vacant label Vacant; sans-serif type; the dark-green theme token for the section title; and the Contact Card Large for each office card.
<<<
RATIONALE: >>>
Those office titles are the Positions the page matches on the leadership list. Vacant is the empty-slot label. Contact Card Large owns card photo, name, title, and contact presentation.
<<<
DERIVED: False
VERIFICATION_METHOD: Test
CHANGE_DRIVER: GSSC5-16
REVIEW_STATUS: Approved
RELATIONS:
- TYPE: Parent
  VALUE: GSSC-PHLR-76
  ROLE: Refines

[[/SECTION]]

[[SECTION]]
UID: GSSC-PLLR-DIRECTORS-AT-LARGE
TITLE: Directors at Large

[REQUIREMENT]
UID: GSSC-PLLR-165
TITLE: Semantic
STATEMENT: >>>
The Directors at Large SHALL retrieve the Unified Backend leadership list, present each Director at Large office with the name of the leader whose Position matches that office when that list includes such a leader with a name, present that leader's preferred contact for contact when the matched entry includes the preferred contact value, present that leader's Account Photo when the matched entry includes Account Photo, and present Vacant when that list has no matching Position or the matching leader has no name.
<<<
RATIONALE: >>>
The leadership list supplies current Director at Large names. Matching by Position fills each Director at Large slot. Preferred contact and Account Photo come from the list entry when present. Vacant marks an empty slot because the list omits empty Position.
<<<
COMMENT: >>>
Canonical Director at Large titles are Lexical. Card chrome is Contact Card Small.
<<<
DERIVED: False
VERIFICATION_METHOD: Test
CHANGE_DRIVER: GSSC5-16
REVIEW_STATUS: Approved
RELATIONS:
- TYPE: Parent
  VALUE: GSSC-PHLR-77
  ROLE: Refines
- TYPE: Parent
  VALUE: GSSC-PHLR-78
  ROLE: Refines
- TYPE: Parent
  VALUE: GSSC-PHLR-79
  ROLE: Refines

[REQUIREMENT]
UID: GSSC-PLLR-166
TITLE: Syntactic
STATEMENT: >>>
The Directors at Large SHALL appear on the public leadership page below Officers and above Committee Chairs as a grid of small contact cards with at most five columns, keep that card cell size when the last row is incomplete, center the remaining cards in that last row, and resize with the page width.
<<<
RATIONALE: >>>
A five-column small-card grid matches five Director at Large seats. Keeping cell size and centering leftovers avoids shrinking leftover cards. Placement between Officers and Committee Chairs matches the page order.
<<<
DERIVED: False
VERIFICATION_METHOD: Test
CHANGE_DRIVER: GSSC5-16
REVIEW_STATUS: Approved
RELATIONS:
- TYPE: Parent
  VALUE: GSSC-PHLR-77
  ROLE: Refines

[REQUIREMENT]
UID: GSSC-PLLR-167
TITLE: Lexical
STATEMENT: >>>
The Directors at Large SHALL use the section title Directors at Large; the office titles Director at Large 1, Director at Large 2, Director at Large 3, Director at Large 4, and Director at Large 5 in that order; the vacant label Vacant; sans-serif type; the dark-green theme token for the section title; and the Contact Card Small for each office card.
<<<
RATIONALE: >>>
Those office titles are the Positions the page matches on the leadership list, in seat order. Vacant is the empty-slot label. Contact Card Small owns card photo, name, title, and contact presentation.
<<<
DERIVED: False
VERIFICATION_METHOD: Test
CHANGE_DRIVER: GSSC5-16
REVIEW_STATUS: Approved
RELATIONS:
- TYPE: Parent
  VALUE: GSSC-PHLR-77
  ROLE: Refines

[[/SECTION]]

[[SECTION]]
UID: GSSC-PLLR-COMMITTEE-CHAIRS
TITLE: Committee Chairs

[REQUIREMENT]
UID: GSSC-PLLR-231
TITLE: Semantic
STATEMENT: >>>
The Committee Chairs SHALL retrieve the Unified Backend leadership list, present each list entry whose Position is not an Officers office and not a Directors at Large office when that entry has a name, present that leader's preferred contact for contact when the entry includes the preferred contact value, and present that leader's Account Photo when the entry includes Account Photo.
<<<
RATIONALE: >>>
Committee chairs are the leadership list entries that are not Officers or Directors at Large. Only entries present on the list with a name appear; empty Positions never appear on the list, so this section does not present Vacant.
<<<
COMMENT: >>>
GSSC5-16 owner follow-up: dynamic chairs from the API; no hardcoded chair roster; no Vacant cards. Card chrome is Contact Card Small. Vacant-chair HLR is not refined here.
<<<
DERIVED: False
VERIFICATION_METHOD: Test
CHANGE_DRIVER: GSSC5-16
REVIEW_STATUS: Approved
RELATIONS:
- TYPE: Parent
  VALUE: GSSC-PHLR-80
  ROLE: Refines
- TYPE: Parent
  VALUE: GSSC-PHLR-81
  ROLE: Refines

[REQUIREMENT]
UID: GSSC-PLLR-232
TITLE: Syntactic
STATEMENT: >>>
The Committee Chairs SHALL appear on the public leadership page below the Directors at Large as a grid of small contact cards with at most five columns, keep that card cell size when the last row is incomplete, center the remaining cards in that last row, present chairs in alphabetical order by Position title, and resize with the page width.
<<<
RATIONALE: >>>
The same small-card grid as Directors at Large keeps chair presentation consistent. Alphabetical Position order makes a dynamic chair list scannable. Placement below Directors matches the page order.
<<<
DERIVED: False
VERIFICATION_METHOD: Test
CHANGE_DRIVER: GSSC5-16
REVIEW_STATUS: Approved
RELATIONS:
- TYPE: Parent
  VALUE: GSSC-PHLR-80
  ROLE: Refines

[REQUIREMENT]
UID: GSSC-PLLR-233
TITLE: Lexical
STATEMENT: >>>
The Committee Chairs SHALL use the section title Committee Chairs; sans-serif type; the dark-green theme token for the section title; and the Contact Card Small for each chair card.
<<<
RATIONALE: >>>
Position titles come from the leadership list at runtime. Contact Card Small owns card photo, name, title, and contact presentation.
<<<
DERIVED: False
VERIFICATION_METHOD: Test
CHANGE_DRIVER: GSSC5-16
REVIEW_STATUS: Approved
RELATIONS:
- TYPE: Parent
  VALUE: GSSC-PHLR-80
  ROLE: Refines

[[/SECTION]]

[[SECTION]]
UID: GSSC-PLLR-CONTACT-CARD-LARGE
TITLE: Contact Card Large

[REQUIREMENT]
UID: GSSC-PLLR-237
TITLE: Semantic
STATEMENT: >>>
The Contact Card Large SHALL present a person's photo when a photo is provided and a person silhouette placeholder when no photo is provided, present the person's name or Vacant, present the person's title, present the preferred contact value when provided, and open a mail or phone draft for that contact when the visitor activates the contact and a contact link is provided.
<<<
RATIONALE: >>>
Large cards show identity, role, and how to reach the person. A silhouette placeholder keeps layout stable when no Account Photo is stored. Activating contact uses mail or phone from the preferred contact fields. Derived because no Public Frontend PIR names a contact card.
<<<
DERIVED: True
VERIFICATION_METHOD: Test
CHANGE_DRIVER: GSSC5-16
REVIEW_STATUS: Approved

[REQUIREMENT]
UID: GSSC-PLLR-238
TITLE: Syntactic
STATEMENT: >>>
The Contact Card Large SHALL place the photo across the top of the card at full card width, place the name, title, and contact below the photo in a vertical stack, and fill the grid cell the page assigns to the card.
<<<
RATIONALE: >>>
A top photo with stacked text below matches the large officer card layout. Filling the assigned grid cell keeps cards aligned in the Officers grid.
<<<
DERIVED: True
VERIFICATION_METHOD: Test
CHANGE_DRIVER: GSSC5-16
REVIEW_STATUS: Approved

[REQUIREMENT]
UID: GSSC-PLLR-239
TITLE: Lexical
STATEMENT: >>>
The Contact Card Large SHALL center the name, title, and contact; present the name slightly larger than body text; present the title in bold; present the contact in italic; use sans-serif type; when filled, use the dark-green theme token for the title, the black theme token for the name and contact, a white background, and the gray theme token for the card border; and when Vacant, use the light-red theme token for the card background and photo area and the dark-red theme token for the title, vacant label, silhouette, and card border.
<<<
RATIONALE: >>>
Centered hierarchy keeps large cards readable. Green/white/gray marks a filled office; red marks Vacant so empty officer slots stand out. A fuller color map is not set yet beyond these token choices.
<<<
DERIVED: True
VERIFICATION_METHOD: Test
CHANGE_DRIVER: GSSC5-16
REVIEW_STATUS: Approved

[[/SECTION]]

[[SECTION]]
UID: GSSC-PLLR-CONTACT-CARD-SMALL
TITLE: Contact Card Small

[REQUIREMENT]
UID: GSSC-PLLR-240
TITLE: Semantic
STATEMENT: >>>
The Contact Card Small SHALL present a person's photo when a photo is provided and a person silhouette placeholder when no photo is provided, present the person's name or Vacant, present the person's title, present the preferred contact value when provided, and open a mail or phone draft for that contact when the visitor activates the contact and a contact link is provided.
<<<
RATIONALE: >>>
Small cards show identity, role, and how to reach the person in a compact form. A silhouette placeholder keeps layout stable when no Account Photo is stored. Activating contact uses mail or phone from the preferred contact fields. Derived because no Public Frontend PIR names a contact card.
<<<
DERIVED: True
VERIFICATION_METHOD: Test
CHANGE_DRIVER: GSSC5-16
REVIEW_STATUS: Approved

[REQUIREMENT]
UID: GSSC-PLLR-241
TITLE: Syntactic
STATEMENT: >>>
The Contact Card Small SHALL place the photo on the left at full card height, place the name, title, and contact in a text column to the right of the photo, and fill the grid cell the page assigns to the card.
<<<
RATIONALE: >>>
A left photo with a text column matches the compact Director and chair card layout. Filling the assigned grid cell keeps cards aligned when the last row is centered.
<<<
DERIVED: True
VERIFICATION_METHOD: Test
CHANGE_DRIVER: GSSC5-16
REVIEW_STATUS: Approved

[REQUIREMENT]
UID: GSSC-PLLR-242
TITLE: Lexical
STATEMENT: >>>
The Contact Card Small SHALL present the name at body text size, present the title in bold, present the contact in italic, use sans-serif type; when filled, use the dark-green theme token for the title, the black theme token for the name and contact, a white background, and the gray theme token for the card border; and when Vacant, use the light-red theme token for the card background and photo area and the dark-red theme token for the title, vacant label, silhouette, and card border.
<<<
RATIONALE: >>>
Default name size and bold title keep small cards dense but readable. Green/white/gray marks a filled seat; red marks Vacant so empty Director at Large slots stand out. A fuller color map is not set yet beyond these token choices.
<<<
DERIVED: True
VERIFICATION_METHOD: Test
CHANGE_DRIVER: GSSC5-16
REVIEW_STATUS: Approved

[[/SECTION]]

[[/SECTION]]

[[SECTION]]
UID: GSSC-PLLR-NEWSLETTERS-PAGE
TITLE: Newsletters Page

[[SECTION]]
UID: GSSC-PLLR-NEWSLETTER-SELECTION-FORM
TITLE: Newsletter Selection Form

[REQUIREMENT]
UID: GSSC-PLLR-207
TITLE: Semantic
STATEMENT: >>>
The Newsletter Selection Form SHALL obtain the newsletter catalog from the Unified Backend, present Volume and Number or Month and Year menus according to the selection mode, select a newsletter from URL query arguments when those arguments identify a catalog entry, and select the most recent newsletter by default when they do not.
<<<
RATIONALE: >>>
The form is the selection path for the page. Query deep links and the newest-default share one catalog.
<<<
DERIVED: False
VERIFICATION_METHOD: Test
CHANGE_DRIVER: GSSC5-20
REVIEW_STATUS: Approved
RELATIONS:
- TYPE: Parent
  VALUE: GSSC-PHLR-121
  ROLE: Refines
- TYPE: Parent
  VALUE: GSSC-PHLR-125
  ROLE: Refines
- TYPE: Parent
  VALUE: GSSC-PHLR-135
  ROLE: Refines

[REQUIREMENT]
UID: GSSC-PLLR-208
TITLE: Syntactic
STATEMENT: >>>
The Newsletter Selection Form SHALL place the mode toggle and active pair of menus on the newsletters page above the selected-newsletter preview and download controls, and below any newsletter intro sections.
<<<
RATIONALE: >>>
Selection stays above the issue presentation and below optional intro content.
<<<
DERIVED: False
VERIFICATION_METHOD: Test
CHANGE_DRIVER: GSSC5-20
REVIEW_STATUS: Approved
RELATIONS:
- TYPE: Parent
  VALUE: GSSC-PHLR-121
  ROLE: Refines

[REQUIREMENT]
UID: GSSC-PLLR-209
TITLE: Lexical
STATEMENT: >>>
The Newsletter Selection Form SHALL use the public sans-serif default typeface, the white theme token for its surface, the dark-green theme token for primary text, and the gray theme token for control borders.
<<<
RATIONALE: >>>
Form chrome follows the public organization palette.
<<<
DERIVED: False
VERIFICATION_METHOD: Test
CHANGE_DRIVER: GSSC5-20
REVIEW_STATUS: Approved
RELATIONS:
- TYPE: Parent
  VALUE: GSSC-PHLR-121
  ROLE: Refines

[[/SECTION]]

[[SECTION]]
UID: GSSC-PLLR-NEWSLETTER-VOLUME-MENU
TITLE: Newsletter Volume Menu

[REQUIREMENT]
UID: GSSC-PLLR-210
TITLE: Semantic
STATEMENT: >>>
The Newsletter Volume Menu SHALL offer each distinct catalog Volume as an option when Volume and Number mode is active, and select the newsletter for that Volume and the current Number when the visitor chooses an option.
<<<
RATIONALE: >>>
Volume options come from the catalog series volumes.
<<<
DERIVED: False
VERIFICATION_METHOD: Test
CHANGE_DRIVER: GSSC5-20
REVIEW_STATUS: Approved
RELATIONS:
- TYPE: Parent
  VALUE: GSSC-PHLR-122
  ROLE: Refines

[REQUIREMENT]
UID: GSSC-PLLR-211
TITLE: Syntactic
STATEMENT: >>>
The Newsletter Volume Menu SHALL appear as a labeled menu within the Newsletter Selection Form beside the Number menu when Volume and Number mode is active.
<<<
RATIONALE: >>>
Volume and Number stay adjacent as a pair.
<<<
DERIVED: False
VERIFICATION_METHOD: Test
CHANGE_DRIVER: GSSC5-20
REVIEW_STATUS: Approved
RELATIONS:
- TYPE: Parent
  VALUE: GSSC-PHLR-122
  ROLE: Refines

[REQUIREMENT]
UID: GSSC-PLLR-212
TITLE: Lexical
STATEMENT: >>>
The Newsletter Volume Menu SHALL use the sans-serif default typeface, the dark-green theme token for its label and value text, the white theme token for its field surface, and the gray theme token for its border.
<<<
RATIONALE: >>>
Menu styling matches other public form controls.
<<<
DERIVED: False
VERIFICATION_METHOD: Test
CHANGE_DRIVER: GSSC5-20
REVIEW_STATUS: Approved
RELATIONS:
- TYPE: Parent
  VALUE: GSSC-PHLR-122
  ROLE: Refines

[[/SECTION]]

[[SECTION]]
UID: GSSC-PLLR-NEWSLETTER-NUMBER-MENU
TITLE: Newsletter Number Menu

[REQUIREMENT]
UID: GSSC-PLLR-213
TITLE: Semantic
STATEMENT: >>>
The Newsletter Number Menu SHALL offer each catalog Number available for the selected Volume when Volume and Number mode is active, and select the newsletter for that Volume and Number when the visitor chooses an option.
<<<
RATIONALE: >>>
Number options follow the issues present for the selected Volume.
<<<
DERIVED: False
VERIFICATION_METHOD: Test
CHANGE_DRIVER: GSSC5-20
REVIEW_STATUS: Approved
RELATIONS:
- TYPE: Parent
  VALUE: GSSC-PHLR-123
  ROLE: Refines

[REQUIREMENT]
UID: GSSC-PLLR-214
TITLE: Syntactic
STATEMENT: >>>
The Newsletter Number Menu SHALL appear as a labeled menu within the Newsletter Selection Form beside the Volume menu when Volume and Number mode is active.
<<<
RATIONALE: >>>
Number sits with Volume as the second half of the pair.
<<<
DERIVED: False
VERIFICATION_METHOD: Test
CHANGE_DRIVER: GSSC5-20
REVIEW_STATUS: Approved
RELATIONS:
- TYPE: Parent
  VALUE: GSSC-PHLR-123
  ROLE: Refines

[REQUIREMENT]
UID: GSSC-PLLR-215
TITLE: Lexical
STATEMENT: >>>
The Newsletter Number Menu SHALL use the sans-serif default typeface, the dark-green theme token for its label and value text, the white theme token for its field surface, and the gray theme token for its border.
<<<
RATIONALE: >>>
Number menu chrome matches the Volume menu.
<<<
DERIVED: False
VERIFICATION_METHOD: Test
CHANGE_DRIVER: GSSC5-20
REVIEW_STATUS: Approved
RELATIONS:
- TYPE: Parent
  VALUE: GSSC-PHLR-123
  ROLE: Refines

[[/SECTION]]

[[SECTION]]
UID: GSSC-PLLR-NEWSLETTER-MONTH-MENU
TITLE: Newsletter Month Menu

[REQUIREMENT]
UID: GSSC-PLLR-216
TITLE: Semantic
STATEMENT: >>>
The Newsletter Month Menu SHALL offer each catalog month available for the selected year when Month and Year mode is active, and select the newsletter for that year and month when the visitor chooses an option.
<<<
RATIONALE: >>>
Month options follow issues present for the selected calendar year.
<<<
DERIVED: False
VERIFICATION_METHOD: Test
CHANGE_DRIVER: GSSC5-20
REVIEW_STATUS: Approved
RELATIONS:
- TYPE: Parent
  VALUE: GSSC-PHLR-130
  ROLE: Refines

[REQUIREMENT]
UID: GSSC-PLLR-217
TITLE: Syntactic
STATEMENT: >>>
The Newsletter Month Menu SHALL appear as a labeled menu within the Newsletter Selection Form beside the Year menu when Month and Year mode is active.
<<<
RATIONALE: >>>
Month and Year stay adjacent as a pair.
<<<
DERIVED: False
VERIFICATION_METHOD: Test
CHANGE_DRIVER: GSSC5-20
REVIEW_STATUS: Approved
RELATIONS:
- TYPE: Parent
  VALUE: GSSC-PHLR-130
  ROLE: Refines

[REQUIREMENT]
UID: GSSC-PLLR-218
TITLE: Lexical
STATEMENT: >>>
The Newsletter Month Menu SHALL use the sans-serif default typeface, the dark-green theme token for its label and value text, the white theme token for its field surface, and the gray theme token for its border.
<<<
RATIONALE: >>>
Month menu chrome matches other selection menus.
<<<
DERIVED: False
VERIFICATION_METHOD: Test
CHANGE_DRIVER: GSSC5-20
REVIEW_STATUS: Approved
RELATIONS:
- TYPE: Parent
  VALUE: GSSC-PHLR-130
  ROLE: Refines

[[/SECTION]]

[[SECTION]]
UID: GSSC-PLLR-NEWSLETTER-YEAR-MENU
TITLE: Newsletter Year Menu

[REQUIREMENT]
UID: GSSC-PLLR-219
TITLE: Semantic
STATEMENT: >>>
The Newsletter Year Menu SHALL offer each distinct catalog year as an option when Month and Year mode is active, and select the newsletter for that year and the current month when the visitor chooses an option.
<<<
RATIONALE: >>>
Year options come from calendar years present in the catalog.
<<<
DERIVED: False
VERIFICATION_METHOD: Test
CHANGE_DRIVER: GSSC5-20
REVIEW_STATUS: Approved
RELATIONS:
- TYPE: Parent
  VALUE: GSSC-PHLR-133
  ROLE: Refines

[REQUIREMENT]
UID: GSSC-PLLR-220
TITLE: Syntactic
STATEMENT: >>>
The Newsletter Year Menu SHALL appear as a labeled menu within the Newsletter Selection Form beside the Month menu when Month and Year mode is active.
<<<
RATIONALE: >>>
Year sits with Month as the calendar selection pair.
<<<
DERIVED: False
VERIFICATION_METHOD: Test
CHANGE_DRIVER: GSSC5-20
REVIEW_STATUS: Approved
RELATIONS:
- TYPE: Parent
  VALUE: GSSC-PHLR-133
  ROLE: Refines

[REQUIREMENT]
UID: GSSC-PLLR-221
TITLE: Lexical
STATEMENT: >>>
The Newsletter Year Menu SHALL use the sans-serif default typeface, the dark-green theme token for its label and value text, the white theme token for its field surface, and the gray theme token for its border.
<<<
RATIONALE: >>>
Year menu chrome matches the Month menu.
<<<
DERIVED: False
VERIFICATION_METHOD: Test
CHANGE_DRIVER: GSSC5-20
REVIEW_STATUS: Approved
RELATIONS:
- TYPE: Parent
  VALUE: GSSC-PHLR-133
  ROLE: Refines

[[/SECTION]]

[[SECTION]]
UID: GSSC-PLLR-NEWSLETTER-MODE-TOGGLE
TITLE: Newsletter Selection Mode Toggle

[REQUIREMENT]
UID: GSSC-PLLR-222
TITLE: Semantic
STATEMENT: >>>
The Newsletter Selection Mode Toggle SHALL switch the Newsletter Selection Form between Volume and Number menus and Month and Year menus without changing the selected newsletter when that newsletter remains in the catalog.
<<<
RATIONALE: >>>
The toggle changes which menus are active while keeping the same issue selected when possible.
<<<
DERIVED: False
VERIFICATION_METHOD: Test
CHANGE_DRIVER: GSSC5-20
REVIEW_STATUS: Approved
RELATIONS:
- TYPE: Parent
  VALUE: GSSC-PHLR-134
  ROLE: Refines

[REQUIREMENT]
UID: GSSC-PLLR-223
TITLE: Syntactic
STATEMENT: >>>
The Newsletter Selection Mode Toggle SHALL appear within the Newsletter Selection Form above the active menu pair.
<<<
RATIONALE: >>>
The toggle precedes the menus it controls.
<<<
DERIVED: False
VERIFICATION_METHOD: Test
CHANGE_DRIVER: GSSC5-20
REVIEW_STATUS: Approved
RELATIONS:
- TYPE: Parent
  VALUE: GSSC-PHLR-134
  ROLE: Refines

[REQUIREMENT]
UID: GSSC-PLLR-224
TITLE: Lexical
STATEMENT: >>>
The Newsletter Selection Mode Toggle SHALL use the sans-serif default typeface, the dark-green theme token for text, and the gray theme token for borders on its controls.
<<<
RATIONALE: >>>
Toggle chrome matches the selection form palette.
<<<
DERIVED: False
VERIFICATION_METHOD: Test
CHANGE_DRIVER: GSSC5-20
REVIEW_STATUS: Approved
RELATIONS:
- TYPE: Parent
  VALUE: GSSC-PHLR-134
  ROLE: Refines

[[/SECTION]]

[[SECTION]]
UID: GSSC-PLLR-NEWSLETTER-PREVIEW
TITLE: Newsletter Preview

[REQUIREMENT]
UID: GSSC-PLLR-225
TITLE: Semantic
STATEMENT: >>>
The Newsletter Preview SHALL present the selected newsletter's issue file from the Unified Backend file identified by that newsletter's file path as an in-page preview.
<<<
RATIONALE: >>>
The newsletter row's file path names the stored file whose bytes the preview shows.
<<<
DERIVED: False
VERIFICATION_METHOD: Test
CHANGE_DRIVER: GSSC5-20
REVIEW_STATUS: Approved
RELATIONS:
- TYPE: Parent
  VALUE: GSSC-PHLR-131
  ROLE: Refines
- TYPE: Parent
  VALUE: GSSC-PHLR-124
  ROLE: Refines

[REQUIREMENT]
UID: GSSC-PLLR-226
TITLE: Syntactic
STATEMENT: >>>
The Newsletter Preview SHALL occupy the primary content area of the newsletters page below the Newsletter Selection Form.
<<<
RATIONALE: >>>
Preview is the main reading surface once an issue is selected.
<<<
DERIVED: False
VERIFICATION_METHOD: Test
CHANGE_DRIVER: GSSC5-20
REVIEW_STATUS: Approved
RELATIONS:
- TYPE: Parent
  VALUE: GSSC-PHLR-131
  ROLE: Refines

[REQUIREMENT]
UID: GSSC-PLLR-227
TITLE: Lexical
STATEMENT: >>>
The Newsletter Preview SHALL use a white theme-token surface, a gray theme-token border, and a minimum preview height large enough to show the issue page content.
<<<
RATIONALE: >>>
A bordered white frame marks the preview region.
<<<
DERIVED: False
VERIFICATION_METHOD: Test
CHANGE_DRIVER: GSSC5-20
REVIEW_STATUS: Approved
RELATIONS:
- TYPE: Parent
  VALUE: GSSC-PHLR-131
  ROLE: Refines

[[/SECTION]]

[[SECTION]]
UID: GSSC-PLLR-NEWSLETTER-DOWNLOAD
TITLE: Newsletter Download

[REQUIREMENT]
UID: GSSC-PLLR-252
TITLE: Semantic
STATEMENT: >>>
The Newsletter Download SHALL provide a download control whose target is the selected newsletter's issue file from the Unified Backend file identified by that newsletter's file path.
<<<
RATIONALE: >>>
Download uses the same stored file as the preview.
<<<
DERIVED: False
VERIFICATION_METHOD: Test
CHANGE_DRIVER: GSSC5-20
REVIEW_STATUS: Approved
RELATIONS:
- TYPE: Parent
  VALUE: GSSC-PHLR-132
  ROLE: Refines

[REQUIREMENT]
UID: GSSC-PLLR-253
TITLE: Syntactic
STATEMENT: >>>
The Newsletter Download SHALL appear adjacent to the Newsletter Preview on the newsletters page.
<<<
RATIONALE: >>>
Download stays with the previewed issue.
<<<
DERIVED: False
VERIFICATION_METHOD: Test
CHANGE_DRIVER: GSSC5-20
REVIEW_STATUS: Approved
RELATIONS:
- TYPE: Parent
  VALUE: GSSC-PHLR-132
  ROLE: Refines

[REQUIREMENT]
UID: GSSC-PLLR-254
TITLE: Lexical
STATEMENT: >>>
The Newsletter Download SHALL present a sans-serif control using the dark-green theme token for text and border and the gray theme token for its hover background.
<<<
RATIONALE: >>>
Download chrome matches other public text controls.
<<<
DERIVED: False
VERIFICATION_METHOD: Test
CHANGE_DRIVER: GSSC5-20
REVIEW_STATUS: Approved
RELATIONS:
- TYPE: Parent
  VALUE: GSSC-PHLR-132
  ROLE: Refines

[[/SECTION]]

[[SECTION]]
UID: GSSC-PLLR-NEWSLETTER-INTRO
TITLE: Newsletter Intro Sections

[REQUIREMENT]
UID: GSSC-PLLR-255
TITLE: Semantic
STATEMENT: >>>
The Newsletter Intro Sections SHALL retrieve public sections tagged for newsletters from the Unified Backend and place each retrieved section through the Section From CUID.
<<<
RATIONALE: >>>
Tagged sections supply optional intro content without hard-coding copy on the page.
<<<
DERIVED: False
VERIFICATION_METHOD: Test
CHANGE_DRIVER: GSSC5-20
REVIEW_STATUS: Approved
RELATIONS:
- TYPE: Parent
  VALUE: GSSC-PHLR-136
  ROLE: Refines

[REQUIREMENT]
UID: GSSC-PLLR-256
TITLE: Syntactic
STATEMENT: >>>
The Newsletter Intro Sections SHALL appear at the top of the newsletters page above the Newsletter Selection Form, place each section through the Section From CUID in backend index order, and omit the intro when the Unified Backend provides no such sections.
<<<
RATIONALE: >>>
Intro precedes selection and preview. Omitting empty intro avoids blank chrome.
<<<
DERIVED: False
VERIFICATION_METHOD: Test
CHANGE_DRIVER: GSSC5-20
REVIEW_STATUS: Approved
RELATIONS:
- TYPE: Parent
  VALUE: GSSC-PHLR-136
  ROLE: Refines

[REQUIREMENT]
UID: GSSC-PLLR-257
TITLE: Lexical
STATEMENT: >>>
The Newsletter Intro Sections SHALL present Section Header, Section Body, and Section Resources through the Section From CUID presentation, without independent lexical chrome of their own.
<<<
RATIONALE: >>>
Intro reuses Section From CUID so newsletters share the Section Container look.
<<<
DERIVED: False
VERIFICATION_METHOD: Test
CHANGE_DRIVER: GSSC5-20
REVIEW_STATUS: Approved
RELATIONS:
- TYPE: Parent
  VALUE: GSSC-PHLR-136
  ROLE: Refines

[[/SECTION]]

[[/SECTION]]

[[SECTION]]
UID: GSSC-PLLR-ROUTER
TITLE: Public Router

[REQUIREMENT]
UID: GSSC-PLLR-8
TITLE: Home Page Route
STATEMENT: >>>
The GSSC Website Public Frontend Router SHALL open the public home page at the root path.
<<<
RATIONALE: >>>
The Navigation Menu reaches the public home page through this route.
<<<
DERIVED: False
VERIFICATION_METHOD: Test
CHANGE_DRIVER: GSSC5-38
REVIEW_STATUS: Approved
RELATIONS:
- TYPE: Parent
  VALUE: GSSC-PHLR-10
  ROLE: Refines

[REQUIREMENT]
UID: GSSC-PLLR-9
TITLE: Membership Information Page Route
STATEMENT: >>>
The GSSC Website Public Frontend Router SHALL open the public membership information page at the membership path.
<<<
RATIONALE: >>>
The Navigation Menu reaches the public membership information page through this route.
<<<
DERIVED: False
VERIFICATION_METHOD: Test
CHANGE_DRIVER: GSSC5-38
REVIEW_STATUS: Approved
RELATIONS:
- TYPE: Parent
  VALUE: GSSC-PHLR-11
  ROLE: Refines

[REQUIREMENT]
UID: GSSC-PLLR-10
TITLE: Leadership Page Route
STATEMENT: >>>
The GSSC Website Public Frontend Router SHALL open the public leadership page at the leadership path.
<<<
RATIONALE: >>>
The Navigation Menu reaches the public leadership page through this route.
<<<
DERIVED: False
VERIFICATION_METHOD: Test
CHANGE_DRIVER: GSSC5-38
REVIEW_STATUS: Approved
RELATIONS:
- TYPE: Parent
  VALUE: GSSC-PHLR-126
  ROLE: Refines

[REQUIREMENT]
UID: GSSC-PLLR-11
TITLE: Calendar Page Route
STATEMENT: >>>
The GSSC Website Public Frontend Router SHALL open the public calendar page at the calendar path.
<<<
RATIONALE: >>>
The Navigation Menu reaches the public calendar through this route.
<<<
DERIVED: False
VERIFICATION_METHOD: Test
CHANGE_DRIVER: GSSC5-38
REVIEW_STATUS: Approved
RELATIONS:
- TYPE: Parent
  VALUE: GSSC-PHLR-12
  ROLE: Refines

[REQUIREMENT]
UID: GSSC-PLLR-12
TITLE: Publications Page Route
STATEMENT: >>>
The GSSC Website Public Frontend Router SHALL open the public publications page at the publications path.
<<<
RATIONALE: >>>
The Navigation Menu reaches the public publications page through this route.
<<<
DERIVED: False
VERIFICATION_METHOD: Test
CHANGE_DRIVER: GSSC5-38
REVIEW_STATUS: Approved
RELATIONS:
- TYPE: Parent
  VALUE: GSSC-PHLR-13
  ROLE: Refines

[REQUIREMENT]
UID: GSSC-PLLR-13
TITLE: Research Tools Page Route
STATEMENT: >>>
The GSSC Website Public Frontend Router SHALL open the public research tools page at the research-tools path.
<<<
RATIONALE: >>>
The Navigation Menu reaches the public research tools page through this route.
<<<
DERIVED: False
VERIFICATION_METHOD: Test
CHANGE_DRIVER: GSSC5-38
REVIEW_STATUS: Approved
RELATIONS:
- TYPE: Parent
  VALUE: GSSC-PHLR-14
  ROLE: Refines

[REQUIREMENT]
UID: GSSC-PLLR-14
TITLE: Newsletters Page Route
STATEMENT: >>>
The GSSC Website Public Frontend Router SHALL open the public newsletters page at the newsletters path.
<<<
RATIONALE: >>>
The Navigation Menu reaches the public newsletters page through this route.
<<<
DERIVED: False
VERIFICATION_METHOD: Test
CHANGE_DRIVER: GSSC5-38
REVIEW_STATUS: Approved
RELATIONS:
- TYPE: Parent
  VALUE: GSSC-PHLR-15
  ROLE: Refines

[[/SECTION]]

[[SECTION]]
UID: GSSC-PLLR-MEMBERSHIP-PAGE
TITLE: Membership Information Page

[[SECTION]]
UID: GSSC-PLLR-MEMBERSHIP-PAGE-ELEMENT
TITLE: Membership Information Page

[REQUIREMENT]
UID: GSSC-PLLR-198
TITLE: Semantic
STATEMENT: >>>
The GSSC Website Public Frontend Membership Information Page SHALL retrieve the public Meeting Information sections and the public Membership Benefits sections from the Unified Backend and place each retrieved section through the Section From CUID.
<<<
RATIONALE: >>>
Meeting Information and Membership Benefits are the membership page Contents. Retrieving those sections from the Unified Backend keeps the wording modifiable. Section From CUID places each section through the Section Container. Membership application is a separate requirement.
<<<
COMMENT: >>>
GSSC5-15. Binding uses backend section tags owned by software; requirements stay tag-agnostic. PHLR-75 application is out of this ticket.
<<<
DERIVED: False
VERIFICATION_METHOD: Test
CHANGE_DRIVER: GSSC5-15
REVIEW_STATUS: Changed
RELATIONS:
- TYPE: Parent
  VALUE: GSSC-PHLR-63
  ROLE: Refines
- TYPE: Parent
  VALUE: GSSC-PHLR-64
  ROLE: Refines
- TYPE: Parent
  VALUE: GSSC-PHLR-65
  ROLE: Refines
- TYPE: Parent
  VALUE: GSSC-PHLR-66
  ROLE: Refines
- TYPE: Parent
  VALUE: GSSC-PHLR-67
  ROLE: Refines

[REQUIREMENT]
UID: GSSC-PLLR-199
TITLE: Syntactic
STATEMENT: >>>
The Membership Information Page SHALL stack Meeting Information above Membership Benefits at full width in the Page Outlet, and SHALL omit a group when the Unified Backend provides no sections for that group.
<<<
RATIONALE: >>>
Meeting Information precedes benefits so a visitor sees where and when the society meets before what membership provides. Full-width stacking matches other public page sections. Omitting an empty group avoids blank chrome when content is absent.
<<<
DERIVED: False
VERIFICATION_METHOD: Test
CHANGE_DRIVER: GSSC5-15
REVIEW_STATUS: Changed
RELATIONS:
- TYPE: Parent
  VALUE: GSSC-PHLR-63
  ROLE: Refines
- TYPE: Parent
  VALUE: GSSC-PHLR-67
  ROLE: Refines

[REQUIREMENT]
UID: GSSC-PLLR-200
TITLE: Lexical
STATEMENT: >>>
The Membership Information Page SHALL inherit the Page Outlet font and text color theme tokens and present Meeting Information and Membership Benefits through the Section From CUID presentation, without independent page chrome of its own.
<<<
RATIONALE: >>>
The page is an assembly of backend sections. Type tokens stay with the Page Outlet; section look stays with Section From CUID and the Section Container so the membership page does not fork a second section presentation.
<<<
DERIVED: False
VERIFICATION_METHOD: Test
CHANGE_DRIVER: GSSC5-15
REVIEW_STATUS: Changed
RELATIONS:
- TYPE: Parent
  VALUE: GSSC-PHLR-63
  ROLE: Refines
- TYPE: Parent
  VALUE: GSSC-PHLR-67
  ROLE: Refines

[[/SECTION]]

[[SECTION]]
UID: GSSC-PLLR-MEMBERSHIP-MEETING
TITLE: Meeting Information

[REQUIREMENT]
UID: GSSC-PLLR-201
TITLE: Semantic
STATEMENT: >>>
The Membership Information Page Meeting Information SHALL present Section Contents that include the general meeting location, the general meeting frequency, the general meeting schedule, and information on the next meeting, as provided by the Unified Backend Meeting Information sections.
<<<
RATIONALE: >>>
Those topics refine the Meeting Information high-level requirements. The backend supplies the wording; the page presents the retrieved Contents without inventing meeting copy.
<<<
DERIVED: False
VERIFICATION_METHOD: Test
CHANGE_DRIVER: GSSC5-15
REVIEW_STATUS: Changed
RELATIONS:
- TYPE: Parent
  VALUE: GSSC-PHLR-63
  ROLE: Refines
- TYPE: Parent
  VALUE: GSSC-PHLR-64
  ROLE: Refines
- TYPE: Parent
  VALUE: GSSC-PHLR-65
  ROLE: Refines
- TYPE: Parent
  VALUE: GSSC-PHLR-66
  ROLE: Refines

[REQUIREMENT]
UID: GSSC-PLLR-202
TITLE: Syntactic
STATEMENT: >>>
The Meeting Information SHALL appear as the first content group on the Membership Information Page and SHALL place each Meeting Information section through the Section From CUID in backend index order.
<<<
RATIONALE: >>>
First placement keeps meeting facts ahead of benefits. Index order preserves the backend's section sequence when more than one Meeting Information section is returned.
<<<
DERIVED: False
VERIFICATION_METHOD: Test
CHANGE_DRIVER: GSSC5-15
REVIEW_STATUS: Changed
RELATIONS:
- TYPE: Parent
  VALUE: GSSC-PHLR-63
  ROLE: Refines

[REQUIREMENT]
UID: GSSC-PLLR-203
TITLE: Lexical
STATEMENT: >>>
The Meeting Information SHALL present its Section Header, Section Body, and Section Resources through the Section From CUID presentation, without independent lexical chrome of its own.
<<<
RATIONALE: >>>
Meeting Information reuses Section From CUID so meeting sections share the Section Container look with other public sections.
<<<
DERIVED: False
VERIFICATION_METHOD: Test
CHANGE_DRIVER: GSSC5-15
REVIEW_STATUS: Changed
RELATIONS:
- TYPE: Parent
  VALUE: GSSC-PHLR-63
  ROLE: Refines

[[/SECTION]]

[[SECTION]]
UID: GSSC-PLLR-MEMBERSHIP-BENEFITS
TITLE: Membership Benefits

[REQUIREMENT]
UID: GSSC-PLLR-204
TITLE: Semantic
STATEMENT: >>>
The Membership Information Page Membership Benefits SHALL present Section Contents that include information on the society's membership benefits, including programs, workshops, seminars, newsletters, queries, surname registration, interest groups, and research trips, as provided by the Unified Backend Membership Benefits sections.
<<<
RATIONALE: >>>
That benefit set refines the Membership Benefit Information high-level requirement. The backend supplies the wording; the page presents the retrieved Contents without inventing benefit copy.
<<<
DERIVED: False
VERIFICATION_METHOD: Test
CHANGE_DRIVER: GSSC5-15
REVIEW_STATUS: Changed
RELATIONS:
- TYPE: Parent
  VALUE: GSSC-PHLR-67
  ROLE: Refines

[REQUIREMENT]
UID: GSSC-PLLR-205
TITLE: Syntactic
STATEMENT: >>>
The Membership Benefits SHALL appear below Meeting Information on the Membership Information Page and SHALL place each Membership Benefits section through the Section From CUID in backend index order.
<<<
RATIONALE: >>>
Benefits follow meeting facts. Index order preserves the backend's section sequence when more than one Membership Benefits section is returned.
<<<
DERIVED: False
VERIFICATION_METHOD: Test
CHANGE_DRIVER: GSSC5-15
REVIEW_STATUS: Changed
RELATIONS:
- TYPE: Parent
  VALUE: GSSC-PHLR-67
  ROLE: Refines

[REQUIREMENT]
UID: GSSC-PLLR-206
TITLE: Lexical
STATEMENT: >>>
The Membership Benefits SHALL present their Section Header, Section Body, and Section Resources through the Section From CUID presentation, without independent lexical chrome of its own.
<<<
RATIONALE: >>>
Membership Benefits reuse Section From CUID so benefit sections share the Section Container look with other public sections.
<<<
DERIVED: False
VERIFICATION_METHOD: Test
CHANGE_DRIVER: GSSC5-15
REVIEW_STATUS: Changed
RELATIONS:
- TYPE: Parent
  VALUE: GSSC-PHLR-67
  ROLE: Refines

[[/SECTION]]

[[/SECTION]]
