[DOCUMENT]
TITLE: Backend Low Level Requirements
UID: GSSC-BACKEND-LOW-LEVEL-REQUIREMENTS
VERSION: 5.0.0

[GRAMMAR]
ELEMENTS:
- TAG: TEXT
  FIELDS:
  - TITLE: UID
    TYPE: String
    REQUIRED: False
  - TITLE: STATEMENT
    TYPE: String
    REQUIRED: True
- TAG: SECTION
  PROPERTIES:
    IS_COMPOSITE: True
    PREFIX: None
    VIEW_STYLE: Narrative
  FIELDS:
  - TITLE: UID
    TYPE: String
    REQUIRED: False
  - TITLE: TITLE
    TYPE: String
    REQUIRED: True
- TAG: REQUIREMENT
  PROPERTIES:
    PREFIX: GSSC-BLLR-
    VIEW_STYLE: Table
  FIELDS:
  - TITLE: UID
    TYPE: String
    REQUIRED: True
  - TITLE: TITLE
    TYPE: String
    REQUIRED: True
  - TITLE: STATEMENT
    TYPE: String
    REQUIRED: True
  - TITLE: RATIONALE
    TYPE: String
    REQUIRED: True
  - TITLE: COMMENT
    TYPE: String
    REQUIRED: False
  - TITLE: DERIVED
    TYPE: SingleChoice(True, False)
    REQUIRED: True
  - TITLE: VERIFICATION_METHOD
    TYPE: SingleChoice(Test, Inspection)
    REQUIRED: True
  - TITLE: CHANGE_DRIVER
    TYPE: String
    REQUIRED: True
  - TITLE: REVIEW_STATUS
    TYPE: SingleChoice(Changed, Approved, Baselined)
    REQUIRED: True
  RELATIONS:
  - TYPE: Parent
    ROLE: Refines
    REVERSE_ROLE: Refined By

[[SECTION]]
UID: GSSC-BLLR-SERVICE-TRANSACTIONS
TITLE: Service Transactions

[[SECTION]]
UID: GSSC-BLLR-USER-ACCOUNTS
TITLE: User Accounts

[[SECTION]]
UID: GSSC-BLLR-ACCOUNT-ACCESS
TITLE: Account Access

[[SECTION]]
UID: GSSC-BLLR-LOGIN
TITLE: /login

[REQUIREMENT]
UID: GSSC-BLLR-1
TITLE: Login Identifiers
STATEMENT: >>>
The GSSC Website Unified Backend SHALL take a member login as a password together with either a Username or a Primary Email.
<<<
RATIONALE: >>>
A member logs in with a password and one account identifier. The identifier is a Username or the Primary Email.
<<<
DERIVED: False
VERIFICATION_METHOD: Test
CHANGE_DRIVER: GSSC5-33
REVIEW_STATUS: Approved
RELATIONS:
- TYPE: Parent
  VALUE: GSSC-BHLR-1
  ROLE: Refines

[REQUIREMENT]
UID: GSSC-BLLR-7
TITLE: Password Match
STATEMENT: >>>
The GSSC Website Unified Backend SHALL log the member in when the supplied Username or Primary Email matches a member and the supplied password matches that member's stored password hash.
<<<
RATIONALE: >>>
The member login succeeds when the identifier locates the member and the password matches the stored password hash. This requirement does not set the hash method.
<<<
DERIVED: False
VERIFICATION_METHOD: Test
CHANGE_DRIVER: GSSC5-33
REVIEW_STATUS: Approved
RELATIONS:
- TYPE: Parent
  VALUE: GSSC-BHLR-1
  ROLE: Refines

[REQUIREMENT]
UID: GSSC-BLLR-11
TITLE: Login Token Lifetime
STATEMENT: >>>
The GSSC Website Unified Backend SHALL take the lifetime of a Login Token from backend configuration. The configured lifetime is a number of days greater than zero. The configured lifetime defaults to seven days.
<<<
RATIONALE: >>>
The time a Login Token remains valid is configuration. The configured lifetime is greater than zero. The configured lifetime defaults to seven days.
<<<
DERIVED: False
VERIFICATION_METHOD: Test
CHANGE_DRIVER: GSSC5-33
REVIEW_STATUS: Approved
RELATIONS:
- TYPE: Parent
  VALUE: GSSC-BHLR-5
  ROLE: Refines

[[SECTION]]
UID: GSSC-BLLR-LOGIN-DATA
TITLE: Data Returned

[REQUIREMENT]
UID: GSSC-BLLR-8
TITLE: Login Token Issued
STATEMENT: >>>
The GSSC Website Unified Backend SHALL issue a Login Token in an HTTP cookie on the successful login response when a member login succeeds.
<<<
RATIONALE: >>>
A successful login yields a Login Token that a later challenge can test. The Login Token is delivered in an HTTP cookie on that response.
<<<
DERIVED: False
VERIFICATION_METHOD: Test
CHANGE_DRIVER: GSSC5-33, GSSC5-48
REVIEW_STATUS: Approved
RELATIONS:
- TYPE: Parent
  VALUE: GSSC-BHLR-2
  ROLE: Refines
- TYPE: Parent
  VALUE: GSSC-BHLR-179
  ROLE: Refines

[REQUIREMENT]
UID: GSSC-BLLR-309
TITLE: Login Token Cookie Storage
STATEMENT: >>>
The GSSC Website Unified Backend SHALL store each Login Token for the client as an HTTP cookie.
<<<
RATIONALE: >>>
The HTTP cookie is the Login Token held by the client. Challenge, logout, and authenticated requests use that cookie.
<<<
DERIVED: False
VERIFICATION_METHOD: Test
CHANGE_DRIVER: GSSC5-48
REVIEW_STATUS: Approved
RELATIONS:
- TYPE: Parent
  VALUE: GSSC-BHLR-179
  ROLE: Refines

[REQUIREMENT]
UID: GSSC-BLLR-292
TITLE: Login Token Cookie HttpOnly
STATEMENT: >>>
The GSSC Website Unified Backend SHALL set the Login Token HTTP cookie so that client script cannot read the cookie value.
<<<
RATIONALE: >>>
HttpOnly keeps the Login Token out of script-readable storage.
<<<
DERIVED: False
VERIFICATION_METHOD: Test
CHANGE_DRIVER: GSSC5-48
REVIEW_STATUS: Approved
RELATIONS:
- TYPE: Parent
  VALUE: GSSC-BHLR-179
  ROLE: Refines

[REQUIREMENT]
UID: GSSC-BLLR-310
TITLE: Login Token Cookie Secure
STATEMENT: >>>
The GSSC Website Unified Backend SHALL mark the Login Token HTTP cookie for secure transport only.
<<<
RATIONALE: >>>
Secure limits the cookie to secure transport.
<<<
DERIVED: False
VERIFICATION_METHOD: Test
CHANGE_DRIVER: GSSC5-48
REVIEW_STATUS: Approved
RELATIONS:
- TYPE: Parent
  VALUE: GSSC-BHLR-179
  ROLE: Refines

[REQUIREMENT]
UID: GSSC-BLLR-311
TITLE: Login Token Cookie SameSite
STATEMENT: >>>
The GSSC Website Unified Backend SHALL set the Login Token HTTP cookie to a lax same-site policy.
<<<
RATIONALE: >>>
SameSite=Lax limits cross-site sending while allowing normal same-site browser use.
<<<
DERIVED: False
VERIFICATION_METHOD: Test
CHANGE_DRIVER: GSSC5-48
REVIEW_STATUS: Approved
RELATIONS:
- TYPE: Parent
  VALUE: GSSC-BHLR-179
  ROLE: Refines

[REQUIREMENT]
UID: GSSC-BLLR-312
TITLE: Login Token Cookie Path
STATEMENT: >>>
The GSSC Website Unified Backend SHALL set the Login Token HTTP cookie path to the site root.
<<<
RATIONALE: >>>
Path=/ applies the cookie to the whole site.
<<<
DERIVED: False
VERIFICATION_METHOD: Test
CHANGE_DRIVER: GSSC5-48
REVIEW_STATUS: Approved
RELATIONS:
- TYPE: Parent
  VALUE: GSSC-BHLR-179
  ROLE: Refines

[REQUIREMENT]
UID: GSSC-BLLR-313
TITLE: Login Token Cookie Max-Age
STATEMENT: >>>
The GSSC Website Unified Backend SHALL set the Login Token HTTP cookie Max-Age to the configured Login Token lifetime in seconds.
<<<
RATIONALE: >>>
Max-Age keeps the cookie lifetime aligned with the Login Token lifetime.
<<<
DERIVED: False
VERIFICATION_METHOD: Test
CHANGE_DRIVER: GSSC5-48
REVIEW_STATUS: Approved
RELATIONS:
- TYPE: Parent
  VALUE: GSSC-BHLR-179
  ROLE: Refines

[[/SECTION]]

[[SECTION]]
UID: GSSC-BLLR-LOGIN-PERSISTENCE
TITLE: Login Token Persistence

[REQUIREMENT]
UID: GSSC-BLLR-315
TITLE: Login Token Hash Stored
STATEMENT: >>>
The GSSC Website Unified Backend SHALL store a hash of the Login Token when a member login succeeds.
<<<
RATIONALE: >>>
The backend retains a hash of the Login Token for later challenge and logout.
<<<
DERIVED: False
VERIFICATION_METHOD: Test
CHANGE_DRIVER: GSSC5-33, GSSC5-48
REVIEW_STATUS: Approved
RELATIONS:
- TYPE: Parent
  VALUE: GSSC-BHLR-182
  ROLE: Refines

[REQUIREMENT]
UID: GSSC-BLLR-316
TITLE: Login Token Row Removed On Logout
STATEMENT: >>>
The GSSC Website Unified Backend SHALL remove the Login Token row when that member logs out that token.
<<<
RATIONALE: >>>
After logout the Login Token is ended. Keeping the row has no further use.
<<<
DERIVED: False
VERIFICATION_METHOD: Test
CHANGE_DRIVER: GSSC5-33, GSSC5-48
REVIEW_STATUS: Approved
RELATIONS:
- TYPE: Parent
  VALUE: GSSC-BHLR-182
  ROLE: Refines
- TYPE: Parent
  VALUE: GSSC-BHLR-4
  ROLE: Refines

[REQUIREMENT]
UID: GSSC-BLLR-317
TITLE: Login Token Rows
STATEMENT: >>>
The GSSC Website Unified Backend SHALL store each Login Token hash in a login tokens table. Each row holds the token hash, the user, the issue time, and the expiry time.
<<<
RATIONALE: >>>
The login tokens table is the durable store for Login Token retention across Unified Backend restarts.
<<<
DERIVED: False
VERIFICATION_METHOD: Test
CHANGE_DRIVER: GSSC5-33, GSSC5-48
REVIEW_STATUS: Approved
RELATIONS:
- TYPE: Parent
  VALUE: GSSC-BHLR-182
  ROLE: Refines

[REQUIREMENT]
UID: GSSC-BLLR-318
TITLE: Login Token Available After Start
STATEMENT: >>>
The GSSC Website Unified Backend SHALL make each retained Login Token available for challenge after the Unified Backend starts.
<<<
RATIONALE: >>>
After a restart, the backend challenges Login Tokens from durable storage. A process-memory-only Login Token would be lost on restart.
<<<
DERIVED: False
VERIFICATION_METHOD: Test
CHANGE_DRIVER: GSSC5-33, GSSC5-48
REVIEW_STATUS: Approved
RELATIONS:
- TYPE: Parent
  VALUE: GSSC-BHLR-182
  ROLE: Refines
- TYPE: Parent
  VALUE: GSSC-BHLR-3
  ROLE: Refines

[REQUIREMENT]
UID: GSSC-BLLR-319
TITLE: Expired Login Token Rows Removed
STATEMENT: >>>
The GSSC Website Unified Backend SHALL remove each Login Token row whose expiry time has elapsed.
<<<
RATIONALE: >>>
An expired Login Token is no longer a current login. Removing the row clears ended sessions from durable storage.
<<<
DERIVED: False
VERIFICATION_METHOD: Test
CHANGE_DRIVER: GSSC5-33, GSSC5-48
REVIEW_STATUS: Approved
RELATIONS:
- TYPE: Parent
  VALUE: GSSC-BHLR-182
  ROLE: Refines
- TYPE: Parent
  VALUE: GSSC-BHLR-5
  ROLE: Refines

[[/SECTION]]

[[SECTION]]
UID: GSSC-BLLR-LOGIN-FAILURES
TITLE: Failure Cases

[REQUIREMENT]
UID: GSSC-BLLR-2
TITLE: Both Identifiers Invalidated
STATEMENT: >>>
The GSSC Website Unified Backend SHALL invalidate a member login that supplies both a Username and a Primary Email.
<<<
RATIONALE: >>>
The login takes one identifier. A login that supplies both a Username and a Primary Email is invalidated.
<<<
DERIVED: False
VERIFICATION_METHOD: Test
CHANGE_DRIVER: GSSC5-33
REVIEW_STATUS: Approved
RELATIONS:
- TYPE: Parent
  VALUE: GSSC-BHLR-1
  ROLE: Refines

[REQUIREMENT]
UID: GSSC-BLLR-3
TITLE: Neither Identifier Invalidated
STATEMENT: >>>
The GSSC Website Unified Backend SHALL invalidate a member login that supplies neither a Username nor a Primary Email.
<<<
RATIONALE: >>>
The login takes one identifier. A login that supplies neither a Username nor a Primary Email is invalidated.
<<<
DERIVED: False
VERIFICATION_METHOD: Test
CHANGE_DRIVER: GSSC5-33
REVIEW_STATUS: Approved
RELATIONS:
- TYPE: Parent
  VALUE: GSSC-BHLR-1
  ROLE: Refines

[REQUIREMENT]
UID: GSSC-BLLR-4
TITLE: Unknown Username Forbidden
STATEMENT: >>>
The GSSC Website Unified Backend SHALL forbid a member login when the supplied Username matches no member.
<<<
RATIONALE: >>>
A Username that matches no member is not a login. The login is forbidden.
<<<
DERIVED: False
VERIFICATION_METHOD: Test
CHANGE_DRIVER: GSSC5-33
REVIEW_STATUS: Approved
RELATIONS:
- TYPE: Parent
  VALUE: GSSC-BHLR-1
  ROLE: Refines

[REQUIREMENT]
UID: GSSC-BLLR-5
TITLE: Unknown Primary Email Forbidden
STATEMENT: >>>
The GSSC Website Unified Backend SHALL forbid a member login when the supplied Primary Email matches no member.
<<<
RATIONALE: >>>
A Primary Email that matches no member is not a login. The login is forbidden.
<<<
DERIVED: False
VERIFICATION_METHOD: Test
CHANGE_DRIVER: GSSC5-33
REVIEW_STATUS: Approved
RELATIONS:
- TYPE: Parent
  VALUE: GSSC-BHLR-1
  ROLE: Refines

[REQUIREMENT]
UID: GSSC-BLLR-6
TITLE: Password Mismatch Forbidden
STATEMENT: >>>
The GSSC Website Unified Backend SHALL forbid a member login when the supplied Username or Primary Email matches a member and the supplied password does not match that member's stored password hash.
<<<
RATIONALE: >>>
The backend compares the supplied password with the member's stored password hash. A password that does not match that hash is forbidden. This requirement does not set the hash method.
<<<
DERIVED: False
VERIFICATION_METHOD: Test
CHANGE_DRIVER: GSSC5-33
REVIEW_STATUS: Approved
RELATIONS:
- TYPE: Parent
  VALUE: GSSC-BHLR-1
  ROLE: Refines

[[/SECTION]]

[[/SECTION]]

[[SECTION]]
UID: GSSC-BLLR-LOGOUT
TITLE: /logout

[REQUIREMENT]
UID: GSSC-BLLR-10
TITLE: Member Logout
STATEMENT: >>>
The GSSC Website Unified Backend SHALL end the member login of a Login Token when that member logs out that token. A later challenge of that Login Token reports it as invalid.
<<<
RATIONALE: >>>
A member ends a login by logging out that Login Token. After logout, the token no longer represents a valid login.
<<<
DERIVED: False
VERIFICATION_METHOD: Test
CHANGE_DRIVER: GSSC5-33
REVIEW_STATUS: Approved
RELATIONS:
- TYPE: Parent
  VALUE: GSSC-BHLR-4
  ROLE: Refines

[REQUIREMENT]
UID: GSSC-BLLR-314
TITLE: Logout Clears Login Token Cookie
STATEMENT: >>>
The GSSC Website Unified Backend SHALL clear the Login Token HTTP cookie on the logout response.
<<<
RATIONALE: >>>
Clearing the cookie ends the session transport for that Login Token.
<<<
DERIVED: False
VERIFICATION_METHOD: Test
CHANGE_DRIVER: GSSC5-48
REVIEW_STATUS: Approved
RELATIONS:
- TYPE: Parent
  VALUE: GSSC-BHLR-4
  ROLE: Refines
- TYPE: Parent
  VALUE: GSSC-BHLR-179
  ROLE: Refines

[[/SECTION]]

[[SECTION]]
UID: GSSC-BLLR-CHALLENGE
TITLE: /challenge

[[SECTION]]
UID: GSSC-BLLR-CHALLENGE-DATA
TITLE: Data Returned

[REQUIREMENT]
UID: GSSC-BLLR-9
TITLE: Login Token Challenge
STATEMENT: >>>
The GSSC Website Unified Backend SHALL report a challenged Login Token as valid or invalid. The report is valid for a Login Token issued for a successful member login that has not expired and has not been logged out. The report does not include the contents of the Login Token.
<<<
RATIONALE: >>>
The challenge tells the caller whether the Login Token is valid without returning the token contents.
<<<
DERIVED: False
VERIFICATION_METHOD: Test
CHANGE_DRIVER: >>>
GSSC5-33
GSSC5-58
<<<
REVIEW_STATUS: Approved
RELATIONS:
- TYPE: Parent
  VALUE: GSSC-BHLR-3
  ROLE: Refines

[REQUIREMENT]
UID: GSSC-BLLR-399
TITLE: Login Token Challenge Member Cuid
STATEMENT: >>>
When a challenged Login Token report is valid, the GSSC Website Unified Backend SHALL include the member cuid for that Login Token in the report.
<<<
RATIONALE: >>>
A valid challenge needs the member cuid so the caller can load that member's account data without receiving the Login Token itself.
<<<
DERIVED: False
VERIFICATION_METHOD: Test
CHANGE_DRIVER: GSSC5-58
REVIEW_STATUS: Approved
RELATIONS:
- TYPE: Parent
  VALUE: GSSC-BHLR-3
  ROLE: Refines

[[/SECTION]]

[REQUIREMENT]
UID: GSSC-BLLR-12
TITLE: Expired Login Token
STATEMENT: >>>
The GSSC Website Unified Backend SHALL expire a Login Token when its lifetime has elapsed since the token was issued. A later challenge of that Login Token reports it as invalid.
<<<
RATIONALE: >>>
A Login Token stops being a valid login when its configured lifetime has elapsed.
<<<
DERIVED: False
VERIFICATION_METHOD: Test
CHANGE_DRIVER: GSSC5-33
REVIEW_STATUS: Approved
RELATIONS:
- TYPE: Parent
  VALUE: GSSC-BHLR-5
  ROLE: Refines

[[/SECTION]]

[[/SECTION]]

[[SECTION]]
UID: GSSC-BLLR-PASSWORD-MANAGEMENT
TITLE: Password Management

[[SECTION]]
UID: GSSC-BLLR-PASSWORD-CHANGE
TITLE: /password/change

[REQUIREMENT]
UID: GSSC-BLLR-224
TITLE: Password Change
STATEMENT: >>>
The GSSC Website Unified Backend SHALL replace a logged-in member's own password through the password change transaction.
<<<
RATIONALE: >>>
A logged-in member replaces that member's password through this transaction.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-247
TITLE: Password Change Login Token Required
STATEMENT: >>>
The GSSC Website Unified Backend SHALL forbid a password change when the request lacks a valid Login Token for that member, and the backend writes nothing.
<<<
RATIONALE: >>>
Only a logged-in member may replace that member's password. A valid Login Token identifies that member.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-225
TITLE: Password Change Inputs
STATEMENT: >>>
The GSSC Website Unified Backend SHALL take a password change as the member's current password and the new password.
<<<
RATIONALE: >>>
The current password confirms the caller holds the existing credential. The new password is the replacement.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-226
TITLE: Password Change Current Match
STATEMENT: >>>
The GSSC Website Unified Backend SHALL replace the member's password when the supplied current password matches that member's stored password hash.
<<<
RATIONALE: >>>
A password change succeeds when the current password matches the stored hash. Separate requirements cover new-password rules.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-227
TITLE: Password Change Current Mismatch
STATEMENT: >>>
The GSSC Website Unified Backend SHALL forbid a password change when the supplied current password does not match that member's stored password hash, and the backend writes nothing.
<<<
RATIONALE: >>>
A wrong current password must not replace the stored hash.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-228
TITLE: Password Change Differs From Current
STATEMENT: >>>
The GSSC Website Unified Backend SHALL invalidate a password change when the member is not the permanent admin account and the new password matches the member's current password hash, and the backend writes nothing.
<<<
RATIONALE: >>>
A replacement password must differ from the current password for every member other than the permanent admin account.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-248
TITLE: Password Change Differs From History
STATEMENT: >>>
The GSSC Website Unified Backend SHALL invalidate a password change when the member is not the permanent admin account and the new password matches any of the last N retained past password hashes, and the backend writes nothing. N is the password history count from backend configuration.
<<<
RATIONALE: >>>
A replacement password must differ from each retained past password for every member other than the permanent admin account.
<<<
DERIVED: False
VERIFICATION_METHOD: Test
CHANGE_DRIVER: GSSC5-35
REVIEW_STATUS: Approved
RELATIONS:
- TYPE: Parent
  VALUE: GSSC-BHLR-20
  ROLE: Refines
- TYPE: Parent
  VALUE: GSSC-BHLR-113
  ROLE: Refines

[REQUIREMENT]
UID: GSSC-BLLR-229
TITLE: Password History Count Configuration
STATEMENT: >>>
The GSSC Website Unified Backend SHALL take the password history count from backend configuration. The configured count is an integer greater than or equal to zero. The configured count defaults to three.
<<<
RATIONALE: >>>
The number of past password hashes the backend retains, and checks on replacement, is configuration and defaults to three.
<<<
DERIVED: False
VERIFICATION_METHOD: Test
CHANGE_DRIVER: GSSC5-35
REVIEW_STATUS: Approved
RELATIONS:
- TYPE: Parent
  VALUE: GSSC-BHLR-113
  ROLE: Refines

[REQUIREMENT]
UID: GSSC-BLLR-230
TITLE: Password Minimum Length Configuration
STATEMENT: >>>
The GSSC Website Unified Backend SHALL take the minimum password length from backend configuration. The configured length is an integer greater than zero. The configured length defaults to eight.
<<<
RATIONALE: >>>
The minimum length of a new password is configuration and defaults to eight.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-249
TITLE: Password Minimum Length
STATEMENT: >>>
The GSSC Website Unified Backend SHALL invalidate a new password that is shorter than the configured minimum length when the member is not the permanent admin account, and the backend writes nothing.
<<<
RATIONALE: >>>
A new password must meet the configured minimum length for every member other than the permanent admin account.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-250
TITLE: Password Required Character Classes
STATEMENT: >>>
The GSSC Website Unified Backend SHALL invalidate a new password that omits a capital letter, a lowercase letter, a number, or a special character when the member is not the permanent admin account, and the backend writes nothing.
<<<
RATIONALE: >>>
A new password must include each required character class for every member other than the permanent admin account.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-251
TITLE: Password Allowed Characters
STATEMENT: >>>
The GSSC Website Unified Backend SHALL invalidate a new password that contains a character outside the allowed set when the member is not the permanent admin account, and the backend writes nothing. The allowed characters are letters, digits, and ` ~ ! @ # $ % ^ & * ( ) _ + - = { } | [ ] \ : " ; ' < > ? , . /
<<<
RATIONALE: >>>
A new password may use only the allowed characters for every member other than the permanent admin account.
<<<
DERIVED: False
VERIFICATION_METHOD: Test
CHANGE_DRIVER: GSSC5-35
REVIEW_STATUS: Approved
RELATIONS:
- TYPE: Parent
  VALUE: GSSC-BHLR-20
  ROLE: Refines

[REQUIREMENT]
UID: GSSC-BLLR-232
TITLE: Permanent Admin Password Replacement
STATEMENT: >>>
The GSSC Website Unified Backend SHALL accept a new password for the permanent admin account when that account replaces its password through password change or password recovery.
<<<
RATIONALE: >>>
The permanent admin account may keep a simple configured password. The length, character, and history invalidations apply only to other members.
<<<
DERIVED: True
VERIFICATION_METHOD: Test
CHANGE_DRIVER: GSSC5-35
REVIEW_STATUS: Approved

[REQUIREMENT]
UID: GSSC-BLLR-233
TITLE: Existing Password Login Validity
STATEMENT: >>>
The GSSC Website Unified Backend SHALL accept a stored password for member login when that password does not meet the new-password length or character rules.
<<<
RATIONALE: >>>
Password rules apply to replacement. No high-level requirement requires accepting a non-conforming stored password for login, so this login acceptance is derived.
<<<
DERIVED: True
VERIFICATION_METHOD: Test
CHANGE_DRIVER: GSSC5-35
REVIEW_STATUS: Approved

[REQUIREMENT]
UID: GSSC-BLLR-234
TITLE: Password Change Stores Current Hash
STATEMENT: >>>
The GSSC Website Unified Backend SHALL store the new password hash as the member's current password hash when a password change succeeds.
<<<
RATIONALE: >>>
A successful replacement updates the current password hash.
<<<
DERIVED: False
VERIFICATION_METHOD: Test
CHANGE_DRIVER: GSSC5-35
REVIEW_STATUS: Approved
RELATIONS:
- TYPE: Parent
  VALUE: GSSC-BHLR-112
  ROLE: Refines

[REQUIREMENT]
UID: GSSC-BLLR-252
TITLE: Password Change Retains History
STATEMENT: >>>
The GSSC Website Unified Backend SHALL retain the previous current password hash in the past password hash history when a password change succeeds.
<<<
RATIONALE: >>>
A successful replacement keeps the previous hash in history. A separate requirement limits how many past hashes the backend keeps.
<<<
DERIVED: False
VERIFICATION_METHOD: Test
CHANGE_DRIVER: GSSC5-35
REVIEW_STATUS: Approved
RELATIONS:
- TYPE: Parent
  VALUE: GSSC-BHLR-113
  ROLE: Refines

[[/SECTION]]

[[SECTION]]
UID: GSSC-BLLR-PASSWORD-RECOVERY-REQUEST
TITLE: /password/recovery-request

[REQUIREMENT]
UID: GSSC-BLLR-235
TITLE: Password Recovery Request Input
STATEMENT: >>>
The GSSC Website Unified Backend SHALL take a password recovery request as an email address.
<<<
RATIONALE: >>>
A recovery request identifies the member by an email address.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-236
TITLE: Password Recovery Message Sent
STATEMENT: >>>
The GSSC Website Unified Backend SHALL send a password recovery message to a member's Primary Email when the recovery request email address matches that Primary Email.
<<<
RATIONALE: >>>
The backend sends recovery mail only to a member's Primary Email. Message wording and layout are out of scope.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-237
TITLE: Password Recovery Request Unknown Email Success
STATEMENT: >>>
The GSSC Website Unified Backend SHALL report success for a password recovery request when the supplied email address matches no member Primary Email.
<<<
RATIONALE: >>>
The response does not reveal whether an address is registered. Success here covers only an unknown address.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-273
TITLE: Password Recovery Request Send Success
STATEMENT: >>>
The GSSC Website Unified Backend SHALL report success for a password recovery request when the backend sends the recovery message.
<<<
RATIONALE: >>>
A completed send ends the recovery request with success.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-274
TITLE: Password Recovery Request Send Server Error
STATEMENT: >>>
The GSSC Website Unified Backend SHALL report a server error for a password recovery request when sending the recovery message fails.
<<<
RATIONALE: >>>
An SMTP send failure is a server-side error and is not reported as success.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-238
TITLE: Password Recovery Token Hash Stored
STATEMENT: >>>
The GSSC Website Unified Backend SHALL store a hash of the recovery token when the backend sends a recovery message.
<<<
RATIONALE: >>>
The backend retains a hash of the recovery token for later verification.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-253
TITLE: Password Recovery Token Plaintext Omitted
STATEMENT: >>>
The GSSC Website Unified Backend SHALL omit the recovery token plaintext from storage.
<<<
RATIONALE: >>>
The backend stores a hash of the recovery token and does not retain the token itself.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-239
TITLE: Password Recovery Token Lifetime Configuration
STATEMENT: >>>
The GSSC Website Unified Backend SHALL take the lifetime of a password recovery token from backend configuration. The configured lifetime is a number of days greater than zero. The configured lifetime defaults to one day.
<<<
RATIONALE: >>>
The backend expires a recovery token after the configured lifetime. The configured lifetime defaults to one day.
<<<
DERIVED: False
VERIFICATION_METHOD: Test
CHANGE_DRIVER: GSSC5-35
REVIEW_STATUS: Approved
RELATIONS:
- TYPE: Parent
  VALUE: GSSC-BHLR-161
  ROLE: Refines

[[/SECTION]]

[[SECTION]]
UID: GSSC-BLLR-PASSWORD-RECOVERY
TITLE: /password/recover

[REQUIREMENT]
UID: GSSC-BLLR-240
TITLE: Password Recovery Inputs
STATEMENT: >>>
The GSSC Website Unified Backend SHALL take a password recovery as a recovery token, the Primary Email paired with that token, and a new password.
<<<
RATIONALE: >>>
The backend takes the token, the Primary Email that received it, and the replacement password.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-254
TITLE: Unknown Recovery Token Forbidden
STATEMENT: >>>
The GSSC Website Unified Backend SHALL forbid a password recovery when the recovery token hash is unknown, and the backend writes nothing.
<<<
RATIONALE: >>>
An unknown recovery token cannot replace a password.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-255
TITLE: Expired Recovery Token Forbidden
STATEMENT: >>>
The GSSC Website Unified Backend SHALL forbid a password recovery when the recovery token lifetime has elapsed, and the backend writes nothing.
<<<
RATIONALE: >>>
An expired recovery token cannot replace a password.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-256
TITLE: Recovery Email Mismatch Forbidden
STATEMENT: >>>
The GSSC Website Unified Backend SHALL forbid a password recovery when the supplied Primary Email does not match the Primary Email paired with that token, and the backend writes nothing.
<<<
RATIONALE: >>>
The Primary Email in the recovery request must match the Primary Email that received the token.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-257
TITLE: Used Recovery Token Forbidden
STATEMENT: >>>
The GSSC Website Unified Backend SHALL forbid a password recovery when the backend has already marked that recovery token as used, and the backend writes nothing.
<<<
RATIONALE: >>>
A recovery token may complete recovery only once.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-268
TITLE: Password Recovery Differs From Current
STATEMENT: >>>
The GSSC Website Unified Backend SHALL invalidate a password recovery when the member is not the permanent admin account and the new password matches the member's current password hash, and the backend writes nothing.
<<<
RATIONALE: >>>
A recovery password must differ from the current password for every member other than the permanent admin account.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-269
TITLE: Password Recovery Differs From History
STATEMENT: >>>
The GSSC Website Unified Backend SHALL invalidate a password recovery when the member is not the permanent admin account and the new password matches any of the last N retained past password hashes, and the backend writes nothing. N is the password history count from backend configuration.
<<<
RATIONALE: >>>
A recovery password must differ from each retained past password for every member other than the permanent admin account.
<<<
DERIVED: False
VERIFICATION_METHOD: Test
CHANGE_DRIVER: GSSC5-35
REVIEW_STATUS: Approved
RELATIONS:
- TYPE: Parent
  VALUE: GSSC-BHLR-161
  ROLE: Refines
- TYPE: Parent
  VALUE: GSSC-BHLR-113
  ROLE: Refines

[REQUIREMENT]
UID: GSSC-BLLR-270
TITLE: Password Recovery Minimum Length
STATEMENT: >>>
The GSSC Website Unified Backend SHALL invalidate a password recovery when the member is not the permanent admin account and the new password is shorter than the configured minimum length, and the backend writes nothing.
<<<
RATIONALE: >>>
A recovery password must meet the configured minimum length for every member other than the permanent admin account.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-271
TITLE: Password Recovery Required Character Classes
STATEMENT: >>>
The GSSC Website Unified Backend SHALL invalidate a password recovery when the member is not the permanent admin account and the new password omits a capital letter, a lowercase letter, a number, or a special character, and the backend writes nothing.
<<<
RATIONALE: >>>
A recovery password must include each required character class for every member other than the permanent admin account.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-272
TITLE: Password Recovery Allowed Characters
STATEMENT: >>>
The GSSC Website Unified Backend SHALL invalidate a password recovery when the member is not the permanent admin account and the new password contains a character outside the allowed set, and the backend writes nothing. The allowed characters are letters, digits, and ` ~ ! @ # $ % ^ & * ( ) _ + - = { } | [ ] \ : " ; ' < > ? , . /
<<<
RATIONALE: >>>
A recovery password may use only the allowed characters for every member other than the permanent admin account.
<<<
DERIVED: False
VERIFICATION_METHOD: Test
CHANGE_DRIVER: GSSC5-35
REVIEW_STATUS: Approved
RELATIONS:
- TYPE: Parent
  VALUE: GSSC-BHLR-161
  ROLE: Refines

[REQUIREMENT]
UID: GSSC-BLLR-258
TITLE: Password Recovery Stores Current Hash
STATEMENT: >>>
The GSSC Website Unified Backend SHALL store the new password hash as the member's current password hash when a password recovery succeeds.
<<<
RATIONALE: >>>
A successful recovery updates the current password hash.
<<<
DERIVED: False
VERIFICATION_METHOD: Test
CHANGE_DRIVER: GSSC5-35
REVIEW_STATUS: Approved
RELATIONS:
- TYPE: Parent
  VALUE: GSSC-BHLR-112
  ROLE: Refines
- TYPE: Parent
  VALUE: GSSC-BHLR-161
  ROLE: Refines

[REQUIREMENT]
UID: GSSC-BLLR-259
TITLE: Password Recovery Retains History
STATEMENT: >>>
The GSSC Website Unified Backend SHALL retain the previous current password hash in the past password hash history when a password recovery succeeds.
<<<
RATIONALE: >>>
A successful recovery keeps the previous hash in history. A separate requirement limits how many past hashes the backend keeps.
<<<
DERIVED: False
VERIFICATION_METHOD: Test
CHANGE_DRIVER: GSSC5-35
REVIEW_STATUS: Approved
RELATIONS:
- TYPE: Parent
  VALUE: GSSC-BHLR-113
  ROLE: Refines
- TYPE: Parent
  VALUE: GSSC-BHLR-161
  ROLE: Refines

[REQUIREMENT]
UID: GSSC-BLLR-260
TITLE: Password Recovery Marks Token Used
STATEMENT: >>>
The GSSC Website Unified Backend SHALL mark the recovery token as used when a password recovery succeeds.
<<<
RATIONALE: >>>
A successful recovery consumes the recovery token.
<<<
DERIVED: False
VERIFICATION_METHOD: Test
CHANGE_DRIVER: GSSC5-35
REVIEW_STATUS: Approved
RELATIONS:
- TYPE: Parent
  VALUE: GSSC-BHLR-161
  ROLE: Refines

[[/SECTION]]

[[/SECTION]]

[[SECTION]]
UID: GSSC-BLLR-ACCOUNT-MANAGEMENT
TITLE: Account Management

[[SECTION]]
UID: GSSC-BLLR-CLEAR-PASSWORDS
TITLE: /users/{cuid}/clear-passwords

[REQUIREMENT]
UID: GSSC-BLLR-263
TITLE: Clear Past Passwords
STATEMENT: >>>
The GSSC Website Unified Backend SHALL delete the past password hashes for the user identified by cuid through the clear-passwords transaction.
<<<
RATIONALE: >>>
A user moderator clears retained past password hashes for a member without changing that member's current password hash.
<<<
DERIVED: True
VERIFICATION_METHOD: Test
CHANGE_DRIVER: >>>
GSSC5-35
GSSC5-36
<<<
REVIEW_STATUS: Approved

[REQUIREMENT]
UID: GSSC-BLLR-264
TITLE: Clear Past Passwords Login Token Required
STATEMENT: >>>
The GSSC Website Unified Backend SHALL forbid a clear-passwords request when the request lacks a valid Login Token in the HTTP cookie, and the backend writes nothing.
<<<
RATIONALE: >>>
Only a logged-in caller may clear past password hashes.
<<<
DERIVED: True
VERIFICATION_METHOD: Test
CHANGE_DRIVER: GSSC5-35, GSSC5-48
REVIEW_STATUS: Approved

[REQUIREMENT]
UID: GSSC-BLLR-265
TITLE: Clear Past Passwords Privilege
STATEMENT: >>>
The GSSC Website Unified Backend SHALL complete a clear-passwords request when the Login Token in the HTTP cookie belongs to a caller who is a user moderator.
<<<
RATIONALE: >>>
Clearing past password hashes is limited to a user moderator.
<<<
DERIVED: True
VERIFICATION_METHOD: Test
CHANGE_DRIVER: >>>
GSSC5-35
GSSC5-36
GSSC5-48
<<<
REVIEW_STATUS: Approved

[REQUIREMENT]
UID: GSSC-BLLR-266
TITLE: Clear Past Passwords Forbidden
STATEMENT: >>>
The GSSC Website Unified Backend SHALL forbid a clear-passwords request when the caller is not a user moderator, and the backend writes nothing.
<<<
RATIONALE: >>>
A caller who is not a user moderator cannot clear past password hashes.
<<<
DERIVED: True
VERIFICATION_METHOD: Test
CHANGE_DRIVER: >>>
GSSC5-35
GSSC5-36
<<<
REVIEW_STATUS: Approved

[REQUIREMENT]
UID: GSSC-BLLR-267
TITLE: Clear Past Passwords User Not Found
STATEMENT: >>>
The GSSC Website Unified Backend SHALL report not found for a clear-passwords request when the cuid matches no user, and the backend writes nothing.
<<<
RATIONALE: >>>
Clearing past password hashes requires a known user cuid.
<<<
DERIVED: True
VERIFICATION_METHOD: Test
CHANGE_DRIVER: GSSC5-35
REVIEW_STATUS: Approved

[[/SECTION]]

[[SECTION]]
UID: GSSC-BLLR-USER-LIST
TITLE: /users

[[SECTION]]
UID: GSSC-BLLR-USER-LIST-DATA
TITLE: Data Returned

[REQUIREMENT]
UID: GSSC-BLLR-41
TITLE: User List
STATEMENT: >>>
The GSSC Website Unified Backend SHALL let a logged-in member retrieve the list of every stored user.
<<<
RATIONALE: >>>
A logged-in member can retrieve the users. The list includes every stored user. Membership Status does not remove a user from the list.
<<<
DERIVED: False
VERIFICATION_METHOD: Test
CHANGE_DRIVER: GSSC5-34
REVIEW_STATUS: Approved
RELATIONS:
- TYPE: Parent
  VALUE: GSSC-BHLR-21
  ROLE: Refines

[REQUIREMENT]
UID: GSSC-BLLR-70
TITLE: User List cuid
STATEMENT: >>>
The GSSC Website Unified Backend SHALL return the cuid in each user list entry to any logged-in member.
<<<
RATIONALE: >>>
Any logged-in member receives this field.
<<<
DERIVED: True
VERIFICATION_METHOD: Test
CHANGE_DRIVER: GSSC5-34
REVIEW_STATUS: Approved

[REQUIREMENT]
UID: GSSC-BLLR-71
TITLE: User List First Name
STATEMENT: >>>
The GSSC Website Unified Backend SHALL return the First Name in each user list entry to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-26
  ROLE: Refines
- TYPE: Parent
  VALUE: GSSC-BHLR-50
  ROLE: Refines
- TYPE: Parent
  VALUE: GSSC-BHLR-70
  ROLE: Refines

[REQUIREMENT]
UID: GSSC-BLLR-72
TITLE: User List Middle Name
STATEMENT: >>>
The GSSC Website Unified Backend SHALL return the Middle Name in each user list entry to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-27
  ROLE: Refines
- TYPE: Parent
  VALUE: GSSC-BHLR-51
  ROLE: Refines
- TYPE: Parent
  VALUE: GSSC-BHLR-71
  ROLE: Refines

[REQUIREMENT]
UID: GSSC-BLLR-73
TITLE: User List Last Name
STATEMENT: >>>
The GSSC Website Unified Backend SHALL return the Last Name in each user list entry to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-28
  ROLE: Refines
- TYPE: Parent
  VALUE: GSSC-BHLR-52
  ROLE: Refines
- TYPE: Parent
  VALUE: GSSC-BHLR-72
  ROLE: Refines

[REQUIREMENT]
UID: GSSC-BLLR-74
TITLE: User List Username
STATEMENT: >>>
The GSSC Website Unified Backend SHALL return the Username in each user list entry when the caller is the user in that entry, or the caller is a user moderator.
<<<
RATIONALE: >>>
The user and a user moderator receive this field. No high-level requirement grants that view to a user moderator, so the moderator grant is derived.
<<<
DERIVED: True
VERIFICATION_METHOD: Test
CHANGE_DRIVER: >>>
GSSC5-34
GSSC5-36
<<<
REVIEW_STATUS: Approved

[REQUIREMENT]
UID: GSSC-BLLR-75
TITLE: User List Primary Email
STATEMENT: >>>
The GSSC Website Unified Backend SHALL return the Primary Email in each user list entry when the caller is the user in that entry, or the caller is a user moderator. The user list also returns the Primary Email to another logged-in member when that user's Preferred Contact Method is Email or None.
<<<
RATIONALE: >>>
The user and a user moderator receive the Primary Email. Another member receives it when the Preferred Contact Method is Email or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-29
  ROLE: Refines
- TYPE: Parent
  VALUE: GSSC-BHLR-53
  ROLE: Refines
- TYPE: Parent
  VALUE: GSSC-BHLR-73
  ROLE: Refines

[REQUIREMENT]
UID: GSSC-BLLR-76
TITLE: User List Secondary Email
STATEMENT: >>>
The GSSC Website Unified Backend SHALL return the Secondary Email in each user list entry when the caller is the user in that entry, or the caller is a user moderator. The user list also returns the Secondary Email to another logged-in member when that user has chosen to display it and the Preferred Contact Method is Email or None.
<<<
RATIONALE: >>>
The user and a user moderator receive the Secondary Email. Another member receives it when it is displayed and the Preferred Contact Method is Email or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-30
  ROLE: Refines
- TYPE: Parent
  VALUE: GSSC-BHLR-54
  ROLE: Refines
- TYPE: Parent
  VALUE: GSSC-BHLR-75
  ROLE: Refines

[REQUIREMENT]
UID: GSSC-BLLR-77
TITLE: User List Primary Phone Number
STATEMENT: >>>
The GSSC Website Unified Backend SHALL return the Primary Phone Number in each user list entry when the caller is the user in that entry, or the caller is a user moderator. The user list also returns the Primary Phone Number to another logged-in member when that user's Preferred Contact Method is Phone or None.
<<<
RATIONALE: >>>
The user and a user moderator receive the Primary Phone Number. Another member receives it when the Preferred Contact Method is Phone or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-31
  ROLE: Refines
- TYPE: Parent
  VALUE: GSSC-BHLR-55
  ROLE: Refines
- TYPE: Parent
  VALUE: GSSC-BHLR-74
  ROLE: Refines

[REQUIREMENT]
UID: GSSC-BLLR-78
TITLE: User List Secondary Phone Number
STATEMENT: >>>
The GSSC Website Unified Backend SHALL return the Secondary Phone Number in each user list entry when the caller is the user in that entry, or the caller is a user moderator. The user list also returns the Secondary Phone Number to another logged-in member when that user has chosen to display it and the Preferred Contact Method is Phone or None.
<<<
RATIONALE: >>>
The user and a user moderator receive the Secondary Phone Number. Another member receives it when it is displayed and the Preferred Contact Method is Phone or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-32
  ROLE: Refines
- TYPE: Parent
  VALUE: GSSC-BHLR-56
  ROLE: Refines
- TYPE: Parent
  VALUE: GSSC-BHLR-76
  ROLE: Refines

[REQUIREMENT]
UID: GSSC-BLLR-79
TITLE: User List Preferred Contact Method
STATEMENT: >>>
The GSSC Website Unified Backend SHALL return the Preferred Contact Method in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-33
  ROLE: Refines
- TYPE: Parent
  VALUE: GSSC-BHLR-57
  ROLE: Refines

[REQUIREMENT]
UID: GSSC-BLLR-80
TITLE: User List Home Address line 1
STATEMENT: >>>
The GSSC Website Unified Backend SHALL return the Home Address line 1 in each user list entry when the caller is the user in that entry, or the caller is a user moderator. The user list also returns the Home Address line 1 to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-81
TITLE: User List Home Address line 2
STATEMENT: >>>
The GSSC Website Unified Backend SHALL return the Home Address line 2 in each user list entry when the caller is the user in that entry, or the caller is a user moderator. The user list also returns the Home Address line 2 to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-82
TITLE: User List Home Address line 3
STATEMENT: >>>
The GSSC Website Unified Backend SHALL return the Home Address line 3 in each user list entry when the caller is the user in that entry, or the caller is a user moderator. The user list also returns the Home Address line 3 to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-83
TITLE: User List Home Address city
STATEMENT: >>>
The GSSC Website Unified Backend SHALL return the Home Address city in each user list entry to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-77
  ROLE: Refines

[REQUIREMENT]
UID: GSSC-BLLR-84
TITLE: User List Home Address state
STATEMENT: >>>
The GSSC Website Unified Backend SHALL return the Home Address state in each user list entry to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-77
  ROLE: Refines

[REQUIREMENT]
UID: GSSC-BLLR-85
TITLE: User List Home Address zip code
STATEMENT: >>>
The GSSC Website Unified Backend SHALL return the Home Address zip code in each user list entry when the caller is the user in that entry, or the caller is a user moderator. The user list also returns the Home Address zip code to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-86
TITLE: User List Home Address zip extension
STATEMENT: >>>
The GSSC Website Unified Backend SHALL return the Home Address zip extension in each user list entry when the caller is the user in that entry, or the caller is a user moderator. The user list also returns the Home Address zip extension to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-87
TITLE: User List Home Address display
STATEMENT: >>>
The GSSC Website Unified Backend SHALL return the Home Address display in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-12
  ROLE: Refines
- TYPE: Parent
  VALUE: GSSC-BHLR-80
  ROLE: Refines

[REQUIREMENT]
UID: GSSC-BLLR-88
TITLE: User List Mailing Address line 1
STATEMENT: >>>
The GSSC Website Unified Backend SHALL return the Mailing Address line 1 in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-89
TITLE: User List Mailing Address line 2
STATEMENT: >>>
The GSSC Website Unified Backend SHALL return the Mailing Address line 2 in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-90
TITLE: User List Mailing Address line 3
STATEMENT: >>>
The GSSC Website Unified Backend SHALL return the Mailing Address line 3 in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-91
TITLE: User List Mailing Address city
STATEMENT: >>>
The GSSC Website Unified Backend SHALL return the Mailing Address city in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-92
TITLE: User List Mailing Address state
STATEMENT: >>>
The GSSC Website Unified Backend SHALL return the Mailing Address state in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-93
TITLE: User List Mailing Address zip code
STATEMENT: >>>
The GSSC Website Unified Backend SHALL return the Mailing Address zip code in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-94
TITLE: User List Mailing Address zip extension
STATEMENT: >>>
The GSSC Website Unified Backend SHALL return the Mailing Address zip extension in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-95
TITLE: User List Secondary Email display
STATEMENT: >>>
The GSSC Website Unified Backend SHALL return the Secondary Email display in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-48
  ROLE: Refines

[REQUIREMENT]
UID: GSSC-BLLR-96
TITLE: User List Secondary Phone Number display
STATEMENT: >>>
The GSSC Website Unified Backend SHALL return the Secondary Phone Number display in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-49
  ROLE: Refines

[REQUIREMENT]
UID: GSSC-BLLR-97
TITLE: User List is administrator
STATEMENT: >>>
The GSSC Website Unified Backend SHALL return the is administrator in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-167
  ROLE: Refines
- TYPE: Parent
  VALUE: GSSC-BHLR-168
  ROLE: Refines

[REQUIREMENT]
UID: GSSC-BLLR-98
TITLE: User List is user moderator
STATEMENT: >>>
The GSSC Website Unified Backend SHALL return the is user moderator in each user list entry when the caller is the user in that entry, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-167
  ROLE: Refines
- TYPE: Parent
  VALUE: GSSC-BHLR-168
  ROLE: Refines

[REQUIREMENT]
UID: GSSC-BLLR-99
TITLE: User List Membership Status
STATEMENT: >>>
The GSSC Website Unified Backend SHALL return the Membership Status in each user list entry when the caller is the user in that entry, or the caller is a user moderator.
<<<
RATIONALE: >>>
The user and a user moderator receive this field. No high-level requirement grants that view to a user moderator, so the moderator grant is derived.
<<<
DERIVED: True
VERIFICATION_METHOD: Test
CHANGE_DRIVER: >>>
GSSC5-34
GSSC5-36
<<<
REVIEW_STATUS: Approved

[REQUIREMENT]
UID: GSSC-BLLR-277
TITLE: User List Position
STATEMENT: >>>
The GSSC Website Unified Backend SHALL return the Position in each user list entry when the caller is the user in that entry, or the caller is a user moderator, including when Position is empty.
<<<
RATIONALE: >>>
The user and a user moderator receive Position, including an empty Position. No high-level requirement grants that view to a user moderator, so the moderator grant is derived.
<<<
DERIVED: False
VERIFICATION_METHOD: Test
CHANGE_DRIVER: >>>
GSSC5-36
<<<
REVIEW_STATUS: Approved
RELATIONS:
- TYPE: Parent
  VALUE: GSSC-BHLR-84
  ROLE: Refines

[REQUIREMENT]
UID: GSSC-BLLR-100
TITLE: User List Password Hash Omitted
STATEMENT: >>>
The GSSC Website Unified Backend SHALL omit the password hash from the user list for every caller, including a caller who is a user moderator.
<<<
RATIONALE: >>>
The user list leaves the password hash out of every entry.
<<<
DERIVED: False
VERIFICATION_METHOD: Test
CHANGE_DRIVER: >>>
GSSC5-34
GSSC5-36
<<<
REVIEW_STATUS: Approved
RELATIONS:
- TYPE: Parent
  VALUE: GSSC-BHLR-112
  ROLE: Refines

[REQUIREMENT]
UID: GSSC-BLLR-44
TITLE: User List First Name Filter
STATEMENT: >>>
The GSSC Website Unified Backend SHALL let a logged-in member filter the user list by a case-insensitive substring of First Name when that member can view First Name.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-101
TITLE: User List Middle Name Filter
STATEMENT: >>>
The GSSC Website Unified Backend SHALL let a logged-in member filter the user list by a case-insensitive substring of Middle Name when that member can view Middle Name.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-102
TITLE: User List Last Name Filter
STATEMENT: >>>
The GSSC Website Unified Backend SHALL let a logged-in member filter the user list by a case-insensitive substring of Last Name when that member can view Last Name.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-103
TITLE: User List Username Filter
STATEMENT: >>>
The GSSC Website Unified Backend SHALL let a logged-in member filter the user list by a case-insensitive substring of Username when that member can view Username.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-104
TITLE: User List Membership Status Filter
STATEMENT: >>>
The GSSC Website Unified Backend SHALL let a logged-in member filter the user list by a case-insensitive substring of Membership Status when that member can view Membership Status.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-105
TITLE: User List Home Address line 1 Filter
STATEMENT: >>>
The GSSC Website Unified Backend SHALL let a logged-in member filter the user list by a case-insensitive substring of Home Address line 1 when that member can view Home Address line 1.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-106
TITLE: User List Home Address line 2 Filter
STATEMENT: >>>
The GSSC Website Unified Backend SHALL let a logged-in member filter the user list by a case-insensitive substring of Home Address line 2 when that member can view Home Address line 2.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-107
TITLE: User List Home Address line 3 Filter
STATEMENT: >>>
The GSSC Website Unified Backend SHALL let a logged-in member filter the user list by a case-insensitive substring of Home Address line 3 when that member can view Home Address line 3.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-108
TITLE: User List Home Address city Filter
STATEMENT: >>>
The GSSC Website Unified Backend SHALL let a logged-in member filter the user list by a case-insensitive substring of Home Address city when that member can view Home Address city.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-109
TITLE: User List Home Address state Filter
STATEMENT: >>>
The GSSC Website Unified Backend SHALL let a logged-in member filter the user list by a case-insensitive substring of Home Address state when that member can view Home Address state.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-110
TITLE: User List Home Address zip code Filter
STATEMENT: >>>
The GSSC Website Unified Backend SHALL let a logged-in member filter the user list by a case-insensitive substring of Home Address zip code when that member can view Home Address zip code.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-111
TITLE: User List Home Address zip extension Filter
STATEMENT: >>>
The GSSC Website Unified Backend SHALL let a logged-in member filter the user list by a case-insensitive substring of Home Address zip extension when that member can view Home Address zip extension.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-112
TITLE: User List Mailing Address line 1 Filter
STATEMENT: >>>
The GSSC Website Unified Backend SHALL let a logged-in member filter the user list by a case-insensitive substring of Mailing Address line 1 when that member can view Mailing Address line 1.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-113
TITLE: User List Mailing Address line 2 Filter
STATEMENT: >>>
The GSSC Website Unified Backend SHALL let a logged-in member filter the user list by a case-insensitive substring of Mailing Address line 2 when that member can view Mailing Address line 2.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-114
TITLE: User List Mailing Address line 3 Filter
STATEMENT: >>>
The GSSC Website Unified Backend SHALL let a logged-in member filter the user list by a case-insensitive substring of Mailing Address line 3 when that member can view Mailing Address line 3.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-115
TITLE: User List Mailing Address city Filter
STATEMENT: >>>
The GSSC Website Unified Backend SHALL let a logged-in member filter the user list by a case-insensitive substring of Mailing Address city when that member can view Mailing Address city.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-116
TITLE: User List Mailing Address state Filter
STATEMENT: >>>
The GSSC Website Unified Backend SHALL let a logged-in member filter the user list by a case-insensitive substring of Mailing Address state when that member can view Mailing Address state.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-117
TITLE: User List Mailing Address zip code Filter
STATEMENT: >>>
The GSSC Website Unified Backend SHALL let a logged-in member filter the user list by a case-insensitive substring of Mailing Address zip code when that member can view Mailing Address zip code.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-118
TITLE: User List Mailing Address zip extension Filter
STATEMENT: >>>
The GSSC Website Unified Backend SHALL let a logged-in member filter the user list by a case-insensitive substring of Mailing Address zip extension when that member can view Mailing Address zip extension.
<<<
RATIONALE: >>>
A logged-in member can filter the list by this text field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-45
TITLE: User List Email Filter
STATEMENT: >>>
The GSSC Website Unified Backend SHALL match an email filter to a case-insensitive substring of the Primary Email or the Secondary Email.
<<<
RATIONALE: >>>
Email is filtered as one contact field across the Primary Email and the Secondary Email.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-119
TITLE: User List Phone Filter
STATEMENT: >>>
The GSSC Website Unified Backend SHALL match a phone filter to a case-insensitive substring of the Primary Phone Number or the Secondary Phone Number.
<<<
RATIONALE: >>>
Phone is filtered as one contact field across the Primary Phone Number and the Secondary Phone Number.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-46
TITLE: User List Preferred Contact Method Filter
STATEMENT: >>>
The GSSC Website Unified Backend SHALL let a logged-in member filter the user list by the full stored value of Preferred Contact Method when that member can view Preferred Contact Method. The comparison ignores case.
<<<
RATIONALE: >>>
A logged-in member can filter by this field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-120
TITLE: User List Home Address display Filter
STATEMENT: >>>
The GSSC Website Unified Backend SHALL let a logged-in member filter the user list by the full stored value of Home Address display when that member can view Home Address display. The comparison ignores case.
<<<
RATIONALE: >>>
A logged-in member can filter by this field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-121
TITLE: User List Secondary Email display Filter
STATEMENT: >>>
The GSSC Website Unified Backend SHALL let a logged-in member filter the user list by the full stored value of Secondary Email display when that member can view Secondary Email display. The comparison ignores case.
<<<
RATIONALE: >>>
A logged-in member can filter by this field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-122
TITLE: User List Secondary Phone Number display Filter
STATEMENT: >>>
The GSSC Website Unified Backend SHALL let a logged-in member filter the user list by the full stored value of Secondary Phone Number display when that member can view Secondary Phone Number display. The comparison ignores case.
<<<
RATIONALE: >>>
A logged-in member can filter by this field when it is in that member's view. The comparison ignores case.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-123
TITLE: User List is administrator Filter
STATEMENT: >>>
The GSSC Website Unified Backend SHALL let a logged-in member filter the user list by the stored true or false value of is administrator when that member can view is administrator.
<<<
RATIONALE: >>>
A logged-in member can filter by this flag when it is in that member's view.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-124
TITLE: User List is user moderator Filter
STATEMENT: >>>
The GSSC Website Unified Backend SHALL let a logged-in member filter the user list by the stored true or false value of is user moderator when that member can view is user moderator.
<<<
RATIONALE: >>>
A logged-in member can filter by this flag when it is in that member's view.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-47
TITLE: User List Filter Match
STATEMENT: >>>
The GSSC Website Unified Backend SHALL include a user in the filtered list when every supplied filter matches.
<<<
RATIONALE: >>>
Every supplied filter has to match before that user is included.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-125
TITLE: User List Hidden Filter Match
STATEMENT: >>>
The GSSC Website Unified Backend SHALL treat a value omitted from that caller's view of that user as a filter match only when the caller is a user moderator.
<<<
RATIONALE: >>>
A hidden value matches a filter for a caller who is a user moderator. For every other caller, a hidden value is not a match.
<<<
DERIVED: False
VERIFICATION_METHOD: Test
CHANGE_DRIVER: >>>
GSSC5-34
GSSC5-36
<<<
REVIEW_STATUS: Approved
RELATIONS:
- TYPE: Parent
  VALUE: GSSC-BHLR-22
  ROLE: Refines

[[/SECTION]]

[[SECTION]]
UID: GSSC-BLLR-USER-LIST-FAILURES
TITLE: Failure Cases

[REQUIREMENT]
UID: GSSC-BLLR-42
TITLE: User List Missing Login Token
STATEMENT: >>>
The GSSC Website Unified Backend SHALL forbid the user list when the Login Token in the HTTP cookie is missing.
<<<
RATIONALE: >>>
A missing Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-21
  ROLE: Refines

[REQUIREMENT]
UID: GSSC-BLLR-67
TITLE: User List Unknown Login Token
STATEMENT: >>>
The GSSC Website Unified Backend SHALL forbid the user list when the Login Token in the HTTP cookie is unknown.
<<<
RATIONALE: >>>
An unknown Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-21
  ROLE: Refines

[REQUIREMENT]
UID: GSSC-BLLR-68
TITLE: User List Logged-Out Login Token
STATEMENT: >>>
The GSSC Website Unified Backend SHALL forbid the user list when the Login Token in the HTTP cookie has been logged out.
<<<
RATIONALE: >>>
A logged-out Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-21
  ROLE: Refines

[REQUIREMENT]
UID: GSSC-BLLR-69
TITLE: User List Expired Login Token
STATEMENT: >>>
The GSSC Website Unified Backend SHALL forbid the user list when the Login Token in the HTTP cookie has expired.
<<<
RATIONALE: >>>
An expired Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-21
  ROLE: Refines

[REQUIREMENT]
UID: GSSC-BLLR-126
TITLE: User List Primary Email Filter Rejected
STATEMENT: >>>
The GSSC Website Unified Backend SHALL invalidate the user list when a filter names the Primary Email alone.
<<<
RATIONALE: >>>
Email and phone are filtered together. A filter that names the Primary Email alone is invalidated.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-127
TITLE: User List Secondary Email Filter Rejected
STATEMENT: >>>
The GSSC Website Unified Backend SHALL invalidate the user list when a filter names the Secondary Email alone.
<<<
RATIONALE: >>>
Email and phone are filtered together. A filter that names the Secondary Email alone is invalidated.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-128
TITLE: User List Primary Phone Filter Rejected
STATEMENT: >>>
The GSSC Website Unified Backend SHALL invalidate the user list when a filter names the Primary Phone Number alone.
<<<
RATIONALE: >>>
Email and phone are filtered together. A filter that names the Primary Phone Number alone is invalidated.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-129
TITLE: User List Secondary Phone Filter Rejected
STATEMENT: >>>
The GSSC Website Unified Backend SHALL invalidate the user list when a filter names the Secondary Phone Number alone.
<<<
RATIONALE: >>>
Email and phone are filtered together. A filter that names the Secondary Phone Number alone is invalidated.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-130
TITLE: User List Hidden Field Filter
STATEMENT: >>>
The GSSC Website Unified Backend SHALL invalidate the user list when a filter names a field that is never in that caller's view.
<<<
RATIONALE: >>>
A filter on a field the caller can never view is invalidated.
<<<
DERIVED: False
VERIFICATION_METHOD: Test
CHANGE_DRIVER: GSSC5-34
REVIEW_STATUS: Approved
RELATIONS:
- TYPE: Parent
  VALUE: GSSC-BHLR-22
  ROLE: Refines

[REQUIREMENT]
UID: GSSC-BLLR-131
TITLE: User List Cuid Filter
STATEMENT: >>>
The GSSC Website Unified Backend SHALL invalidate the user list when a filter names the cuid.
<<<
RATIONALE: >>>
The cuid is not a filter field.
<<<
DERIVED: True
VERIFICATION_METHOD: Test
CHANGE_DRIVER: GSSC5-34
REVIEW_STATUS: Approved

[REQUIREMENT]
UID: GSSC-BLLR-132
TITLE: User List Password Hash Filter
STATEMENT: >>>
The GSSC Website Unified Backend SHALL invalidate the user list when a filter names the password hash.
<<<
RATIONALE: >>>
The password hash is not a filter field.
<<<
DERIVED: False
VERIFICATION_METHOD: Test
CHANGE_DRIVER: GSSC5-34
REVIEW_STATUS: Approved
RELATIONS:
- TYPE: Parent
  VALUE: GSSC-BHLR-112
  ROLE: Refines

[[/SECTION]]

[[/SECTION]]

[[SECTION]]
UID: GSSC-BLLR-USER-RECORD
TITLE: /users/{cuid}

[[SECTION]]
UID: GSSC-BLLR-USER-GET
TITLE: GET

[[SECTION]]
UID: GSSC-BLLR-USER-GET-DATA
TITLE: Data Returned

[REQUIREMENT]
UID: GSSC-BLLR-49
TITLE: User Read Subject
STATEMENT: >>>
The GSSC Website Unified Backend SHALL return fields for the user identified by the cuid in the path.
<<<
RATIONALE: >>>
The user read is about the user named by the cuid. Each returned field is its own requirement.
<<<
DERIVED: False
VERIFICATION_METHOD: Test
CHANGE_DRIVER: GSSC5-34
REVIEW_STATUS: Approved
RELATIONS:
- TYPE: Parent
  VALUE: GSSC-BHLR-26
  ROLE: Refines

[REQUIREMENT]
UID: GSSC-BLLR-136
TITLE: User Read cuid
STATEMENT: >>>
The GSSC Website Unified Backend SHALL return the cuid of the user identified by the cuid to any logged-in member.
<<<
RATIONALE: >>>
Any logged-in member receives this field.
<<<
DERIVED: True
VERIFICATION_METHOD: Test
CHANGE_DRIVER: GSSC5-34
REVIEW_STATUS: Approved

[REQUIREMENT]
UID: GSSC-BLLR-137
TITLE: User Read First Name
STATEMENT: >>>
The GSSC Website Unified Backend SHALL return the First Name of the user identified by the cuid to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-26
  ROLE: Refines
- TYPE: Parent
  VALUE: GSSC-BHLR-50
  ROLE: Refines
- TYPE: Parent
  VALUE: GSSC-BHLR-70
  ROLE: Refines

[REQUIREMENT]
UID: GSSC-BLLR-138
TITLE: User Read Middle Name
STATEMENT: >>>
The GSSC Website Unified Backend SHALL return the Middle Name of the user identified by the cuid to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-27
  ROLE: Refines
- TYPE: Parent
  VALUE: GSSC-BHLR-51
  ROLE: Refines
- TYPE: Parent
  VALUE: GSSC-BHLR-71
  ROLE: Refines

[REQUIREMENT]
UID: GSSC-BLLR-139
TITLE: User Read Last Name
STATEMENT: >>>
The GSSC Website Unified Backend SHALL return the Last Name of the user identified by the cuid to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-28
  ROLE: Refines
- TYPE: Parent
  VALUE: GSSC-BHLR-52
  ROLE: Refines
- TYPE: Parent
  VALUE: GSSC-BHLR-72
  ROLE: Refines

[REQUIREMENT]
UID: GSSC-BLLR-140
TITLE: User Read Username
STATEMENT: >>>
The GSSC Website Unified Backend SHALL return the Username of the user identified by the cuid when the caller is that user, or the caller is a user moderator.
<<<
RATIONALE: >>>
The user and a user moderator receive this field. No high-level requirement grants that view to a user moderator, so the moderator grant is derived.
<<<
DERIVED: True
VERIFICATION_METHOD: Test
CHANGE_DRIVER: >>>
GSSC5-34
GSSC5-36
<<<
REVIEW_STATUS: Approved

[REQUIREMENT]
UID: GSSC-BLLR-141
TITLE: User Read Primary Email
STATEMENT: >>>
The GSSC Website Unified Backend SHALL return the Primary Email of the user identified by the cuid when the caller is that user, or the caller is a user moderator. The user read also returns the Primary Email to another logged-in member when that user's Preferred Contact Method is Email or None.
<<<
RATIONALE: >>>
The user and a user moderator receive the Primary Email. Another member receives it when the Preferred Contact Method is Email or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-29
  ROLE: Refines
- TYPE: Parent
  VALUE: GSSC-BHLR-53
  ROLE: Refines
- TYPE: Parent
  VALUE: GSSC-BHLR-73
  ROLE: Refines

[REQUIREMENT]
UID: GSSC-BLLR-142
TITLE: User Read Secondary Email
STATEMENT: >>>
The GSSC Website Unified Backend SHALL return the Secondary Email of the user identified by the cuid when the caller is that user, or the caller is a user moderator. The user read also returns the Secondary Email to another logged-in member when that user has chosen to display it and the Preferred Contact Method is Email or None.
<<<
RATIONALE: >>>
The user and a user moderator receive the Secondary Email. Another member receives it when it is displayed and the Preferred Contact Method is Email or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-30
  ROLE: Refines
- TYPE: Parent
  VALUE: GSSC-BHLR-54
  ROLE: Refines
- TYPE: Parent
  VALUE: GSSC-BHLR-75
  ROLE: Refines

[REQUIREMENT]
UID: GSSC-BLLR-143
TITLE: User Read Primary Phone Number
STATEMENT: >>>
The GSSC Website Unified Backend SHALL return the Primary Phone Number of the user identified by the cuid when the caller is that user, or the caller is a user moderator. The user read also returns the Primary Phone Number to another logged-in member when that user's Preferred Contact Method is Phone or None.
<<<
RATIONALE: >>>
The user and a user moderator receive the Primary Phone Number. Another member receives it when the Preferred Contact Method is Phone or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-31
  ROLE: Refines
- TYPE: Parent
  VALUE: GSSC-BHLR-55
  ROLE: Refines
- TYPE: Parent
  VALUE: GSSC-BHLR-74
  ROLE: Refines

[REQUIREMENT]
UID: GSSC-BLLR-144
TITLE: User Read Secondary Phone Number
STATEMENT: >>>
The GSSC Website Unified Backend SHALL return the Secondary Phone Number of the user identified by the cuid when the caller is that user, or the caller is a user moderator. The user read also returns the Secondary Phone Number to another logged-in member when that user has chosen to display it and the Preferred Contact Method is Phone or None.
<<<
RATIONALE: >>>
The user and a user moderator receive the Secondary Phone Number. Another member receives it when it is displayed and the Preferred Contact Method is Phone or None. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-32
  ROLE: Refines
- TYPE: Parent
  VALUE: GSSC-BHLR-56
  ROLE: Refines
- TYPE: Parent
  VALUE: GSSC-BHLR-76
  ROLE: Refines

[REQUIREMENT]
UID: GSSC-BLLR-145
TITLE: User Read Preferred Contact Method
STATEMENT: >>>
The GSSC Website Unified Backend SHALL return the Preferred Contact Method of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-33
  ROLE: Refines
- TYPE: Parent
  VALUE: GSSC-BHLR-57
  ROLE: Refines

[REQUIREMENT]
UID: GSSC-BLLR-146
TITLE: User Read Home Address line 1
STATEMENT: >>>
The GSSC Website Unified Backend SHALL return the Home Address line 1 of the user identified by the cuid when the caller is that user, or the caller is a user moderator. The user read also returns the Home Address line 1 to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-147
TITLE: User Read Home Address line 2
STATEMENT: >>>
The GSSC Website Unified Backend SHALL return the Home Address line 2 of the user identified by the cuid when the caller is that user, or the caller is a user moderator. The user read also returns the Home Address line 2 to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-148
TITLE: User Read Home Address line 3
STATEMENT: >>>
The GSSC Website Unified Backend SHALL return the Home Address line 3 of the user identified by the cuid when the caller is that user, or the caller is a user moderator. The user read also returns the Home Address line 3 to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-149
TITLE: User Read Home Address city
STATEMENT: >>>
The GSSC Website Unified Backend SHALL return the Home Address city of the user identified by the cuid to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-77
  ROLE: Refines

[REQUIREMENT]
UID: GSSC-BLLR-150
TITLE: User Read Home Address state
STATEMENT: >>>
The GSSC Website Unified Backend SHALL return the Home Address state of the user identified by the cuid to any logged-in member.
<<<
RATIONALE: >>>
Any logged-in member receives this field.
<<<
DERIVED: False
VERIFICATION_METHOD: Test
CHANGE_DRIVER: GSSC5-34
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-77
  ROLE: Refines

[REQUIREMENT]
UID: GSSC-BLLR-151
TITLE: User Read Home Address zip code
STATEMENT: >>>
The GSSC Website Unified Backend SHALL return the Home Address zip code of the user identified by the cuid when the caller is that user, or the caller is a user moderator. The user read also returns the Home Address zip code to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-152
TITLE: User Read Home Address zip extension
STATEMENT: >>>
The GSSC Website Unified Backend SHALL return the Home Address zip extension of the user identified by the cuid when the caller is that user, or the caller is a user moderator. The user read also returns the Home Address zip extension to another logged-in member when that user's Home Address display is full.
<<<
RATIONALE: >>>
The user and a user moderator receive this Home Address part. Another member receives it when the Home Address display is full. The moderator grant is derived.
<<<
DERIVED: False
VERIFICATION_METHOD: Test
CHANGE_DRIVER: >>>
GSSC5-34
GSSC5-36
<<<
REVIEW_STATUS: Approved
RELATIONS:
- TYPE: Parent
  VALUE: GSSC-BHLR-34
  ROLE: Refines
- TYPE: Parent
  VALUE: GSSC-BHLR-58
  ROLE: Refines
- TYPE: Parent
  VALUE: GSSC-BHLR-78
  ROLE: Refines

[REQUIREMENT]
UID: GSSC-BLLR-153
TITLE: User Read Home Address display
STATEMENT: >>>
The GSSC Website Unified Backend SHALL return the Home Address display of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-12
  ROLE: Refines
- TYPE: Parent
  VALUE: GSSC-BHLR-80
  ROLE: Refines

[REQUIREMENT]
UID: GSSC-BLLR-154
TITLE: User Read Mailing Address line 1
STATEMENT: >>>
The GSSC Website Unified Backend SHALL return the Mailing Address line 1 of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-155
TITLE: User Read Mailing Address line 2
STATEMENT: >>>
The GSSC Website Unified Backend SHALL return the Mailing Address line 2 of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-156
TITLE: User Read Mailing Address line 3
STATEMENT: >>>
The GSSC Website Unified Backend SHALL return the Mailing Address line 3 of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-157
TITLE: User Read Mailing Address city
STATEMENT: >>>
The GSSC Website Unified Backend SHALL return the Mailing Address city of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-158
TITLE: User Read Mailing Address state
STATEMENT: >>>
The GSSC Website Unified Backend SHALL return the Mailing Address state of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-159
TITLE: User Read Mailing Address zip code
STATEMENT: >>>
The GSSC Website Unified Backend SHALL return the Mailing Address zip code of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-160
TITLE: User Read Mailing Address zip extension
STATEMENT: >>>
The GSSC Website Unified Backend SHALL return the Mailing Address zip extension of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-35
  ROLE: Refines
- TYPE: Parent
  VALUE: GSSC-BHLR-59
  ROLE: Refines

[REQUIREMENT]
UID: GSSC-BLLR-161
TITLE: User Read Secondary Email display
STATEMENT: >>>
The GSSC Website Unified Backend SHALL return the Secondary Email display of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-48
  ROLE: Refines

[REQUIREMENT]
UID: GSSC-BLLR-162
TITLE: User Read Secondary Phone Number display
STATEMENT: >>>
The GSSC Website Unified Backend SHALL return the Secondary Phone Number display of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-49
  ROLE: Refines

[REQUIREMENT]
UID: GSSC-BLLR-163
TITLE: User Read is administrator
STATEMENT: >>>
The GSSC Website Unified Backend SHALL return the is administrator of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-167
  ROLE: Refines
- TYPE: Parent
  VALUE: GSSC-BHLR-168
  ROLE: Refines

[REQUIREMENT]
UID: GSSC-BLLR-164
TITLE: User Read is user moderator
STATEMENT: >>>
The GSSC Website Unified Backend SHALL return the is user moderator of the user identified by the cuid when the caller is that user, or the caller is a user moderator.
<<<
RATIONALE: >>>
The user and a user moderator receive this field. No high-level requirement grants that view to a user moderator, so the moderator grant is derived.
<<<
DERIVED: False
VERIFICATION_METHOD: Test
CHANGE_DRIVER: >>>
GSSC5-34
GSSC5-36
<<<
REVIEW_STATUS: Approved
RELATIONS:
- TYPE: Parent
  VALUE: GSSC-BHLR-167
  ROLE: Refines
- TYPE: Parent
  VALUE: GSSC-BHLR-168
  ROLE: Refines

[REQUIREMENT]
UID: GSSC-BLLR-165
TITLE: User Read Membership Status
STATEMENT: >>>
The GSSC Website Unified Backend SHALL return the Membership Status of the user identified by the cuid when the caller is that user, or the caller is a user moderator.
<<<
RATIONALE: >>>
The user and a user moderator receive this field. No high-level requirement grants that view to a user moderator, so the moderator grant is derived.
<<<
DERIVED: True
VERIFICATION_METHOD: Test
CHANGE_DRIVER: >>>
GSSC5-34
GSSC5-36
<<<
REVIEW_STATUS: Approved

[REQUIREMENT]
UID: GSSC-BLLR-278
TITLE: User Read Position
STATEMENT: >>>
The GSSC Website Unified Backend SHALL return the Position of the user identified by the cuid when the caller is that user, or the caller is a user moderator, including when Position is empty.
<<<
RATIONALE: >>>
The user and a user moderator receive Position, including an empty Position. No high-level requirement grants that view to a user moderator, so the moderator grant is derived.
<<<
DERIVED: False
VERIFICATION_METHOD: Test
CHANGE_DRIVER: >>>
GSSC5-36
<<<
REVIEW_STATUS: Approved
RELATIONS:
- TYPE: Parent
  VALUE: GSSC-BHLR-84
  ROLE: Refines

[REQUIREMENT]
UID: GSSC-BLLR-54
TITLE: Password Hash Omitted
STATEMENT: >>>
The GSSC Website Unified Backend SHALL omit the password hash from the user read for every caller, including a caller who is a user moderator.
<<<
RATIONALE: >>>
The user read leaves the password hash out of every response.
<<<
DERIVED: False
VERIFICATION_METHOD: Test
CHANGE_DRIVER: >>>
GSSC5-34
GSSC5-36
<<<
REVIEW_STATUS: Approved
RELATIONS:
- TYPE: Parent
  VALUE: GSSC-BHLR-112
  ROLE: Refines

[[/SECTION]]

[[SECTION]]
UID: GSSC-BLLR-USER-GET-FAILURES
TITLE: Failure Cases

[REQUIREMENT]
UID: GSSC-BLLR-48
TITLE: User Read Missing Login Token
STATEMENT: >>>
The GSSC Website Unified Backend SHALL forbid the user read when the Login Token in the HTTP cookie is missing.
<<<
RATIONALE: >>>
A missing Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-26
  ROLE: Refines

[REQUIREMENT]
UID: GSSC-BLLR-133
TITLE: User Read Unknown Login Token
STATEMENT: >>>
The GSSC Website Unified Backend SHALL forbid the user read when the Login Token in the HTTP cookie is unknown.
<<<
RATIONALE: >>>
An unknown Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-26
  ROLE: Refines

[REQUIREMENT]
UID: GSSC-BLLR-134
TITLE: User Read Logged-Out Login Token
STATEMENT: >>>
The GSSC Website Unified Backend SHALL forbid the user read when the Login Token in the HTTP cookie has been logged out.
<<<
RATIONALE: >>>
A logged-out Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-26
  ROLE: Refines

[REQUIREMENT]
UID: GSSC-BLLR-135
TITLE: User Read Expired Login Token
STATEMENT: >>>
The GSSC Website Unified Backend SHALL forbid the user read when the Login Token in the HTTP cookie has expired.
<<<
RATIONALE: >>>
An expired Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-26
  ROLE: Refines

[REQUIREMENT]
UID: GSSC-BLLR-55
TITLE: User Not Found
STATEMENT: >>>
The GSSC Website Unified Backend SHALL report the user not found when the user read names a cuid that no user has. The report is the same for every logged-in caller.
<<<
RATIONALE: >>>
A cuid that belongs to no user is a missing record. The report is the same for every logged-in caller because a cuid is not private. The test binds this report to HTTP 404. A cuid that exists still returns the allowed fields.
<<<
DERIVED: True
VERIFICATION_METHOD: Test
CHANGE_DRIVER: GSSC5-34
REVIEW_STATUS: Approved

[[/SECTION]]

[[/SECTION]]

[[SECTION]]
UID: GSSC-BLLR-USER-POST
TITLE: POST

[[SECTION]]
UID: GSSC-BLLR-USER-POST-DATA
TITLE: Data Updated

[REQUIREMENT]
UID: GSSC-BLLR-58
TITLE: Administrator User Update
STATEMENT: >>>
The GSSC Website Unified Backend SHALL apply the user update when the caller is an administrator, including when the cuid is that caller's own cuid.
<<<
RATIONALE: >>>
An administrator can update any user, including that administrator's own record.
<<<
DERIVED: False
VERIFICATION_METHOD: Test
CHANGE_DRIVER: GSSC5-34
REVIEW_STATUS: Approved
RELATIONS:
- TYPE: Parent
  VALUE: GSSC-BHLR-60
  ROLE: Refines

[REQUIREMENT]
UID: GSSC-BLLR-169
TITLE: Own User Update
STATEMENT: >>>
The GSSC Website Unified Backend SHALL apply the user update when the cuid is the caller's own cuid and that user is not an administrator.
<<<
RATIONALE: >>>
A member who is not an administrator can update that member's own account.
<<<
DERIVED: False
VERIFICATION_METHOD: Test
CHANGE_DRIVER: GSSC5-34
REVIEW_STATUS: Approved
RELATIONS:
- TYPE: Parent
  VALUE: GSSC-BHLR-36
  ROLE: Refines

[REQUIREMENT]
UID: GSSC-BLLR-170
TITLE: User Moderator User Update
STATEMENT: >>>
The GSSC Website Unified Backend SHALL apply the user update when the caller is a user moderator and the user identified by the cuid is not an administrator.
<<<
RATIONALE: >>>
A user moderator can update a user who is not an administrator. No high-level requirement grants that update.
<<<
DERIVED: True
VERIFICATION_METHOD: Test
CHANGE_DRIVER: GSSC5-34
REVIEW_STATUS: Approved

[REQUIREMENT]
UID: GSSC-BLLR-172
TITLE: User Update Omitted Fields
STATEMENT: >>>
The GSSC Website Unified Backend SHALL leave every omitted account field unchanged when the user update is stored.
<<<
RATIONALE: >>>
The update changes the fields included in the request. Every field left out of the request stays as stored.
<<<
DERIVED: True
VERIFICATION_METHOD: Test
CHANGE_DRIVER: GSSC5-34
REVIEW_STATUS: Approved

[REQUIREMENT]
UID: GSSC-BLLR-174
TITLE: User Update First Name
STATEMENT: >>>
The GSSC Website Unified Backend SHALL store a posted First Name when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-36
  ROLE: Refines
- TYPE: Parent
  VALUE: GSSC-BHLR-60
  ROLE: Refines

[REQUIREMENT]
UID: GSSC-BLLR-176
TITLE: User Update Middle Name
STATEMENT: >>>
The GSSC Website Unified Backend SHALL store a posted Middle Name when the caller is an administrator, when the cuid is the caller's own cuid and that user is not an administrator, or when the caller is a user moderator and the user identified by the cuid is not an administrator. An included Middle Name of "" clears the Middle Name.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-37
  ROLE: Refines
- TYPE: Parent
  VALUE: GSSC-BHLR-61
  ROLE: Refines

[REQUIREMENT]
UID: GSSC-BLLR-177
TITLE: User Update Last Name
STATEMENT: >>>
The GSSC Website Unified Backend SHALL store a posted Last Name when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-38
  ROLE: Refines
- TYPE: Parent
  VALUE: GSSC-BHLR-62
  ROLE: Refines

[REQUIREMENT]
UID: GSSC-BLLR-179
TITLE: User Update Primary Email
STATEMENT: >>>
The GSSC Website Unified Backend SHALL store a posted Primary Email when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-39
  ROLE: Refines
- TYPE: Parent
  VALUE: GSSC-BHLR-63
  ROLE: Refines

[REQUIREMENT]
UID: GSSC-BLLR-181
TITLE: User Update Secondary Email
STATEMENT: >>>
The GSSC Website Unified Backend SHALL store a posted Secondary Email when the caller is an administrator, when the cuid is the caller's own cuid and that user is not an administrator, or when the caller is a user moderator and the user identified by the cuid is not an administrator. An included Secondary Email of "" clears the Secondary Email.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-40
  ROLE: Refines
- TYPE: Parent
  VALUE: GSSC-BHLR-64
  ROLE: Refines

[REQUIREMENT]
UID: GSSC-BLLR-182
TITLE: User Update Primary Phone Number
STATEMENT: >>>
The GSSC Website Unified Backend SHALL store a posted Primary Phone Number when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-41
  ROLE: Refines
- TYPE: Parent
  VALUE: GSSC-BHLR-65
  ROLE: Refines

[REQUIREMENT]
UID: GSSC-BLLR-184
TITLE: User Update Secondary Phone Number
STATEMENT: >>>
The GSSC Website Unified Backend SHALL store a posted Secondary Phone Number when the caller is an administrator, when the cuid is the caller's own cuid and that user is not an administrator, or when the caller is a user moderator and the user identified by the cuid is not an administrator. An included Secondary Phone Number of "" clears the Secondary Phone Number.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-42
  ROLE: Refines
- TYPE: Parent
  VALUE: GSSC-BHLR-66
  ROLE: Refines

[REQUIREMENT]
UID: GSSC-BLLR-185
TITLE: User Update Preferred Contact Method
STATEMENT: >>>
The GSSC Website Unified Backend SHALL store a posted Preferred Contact Method when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-43
  ROLE: Refines
- TYPE: Parent
  VALUE: GSSC-BHLR-67
  ROLE: Refines

[REQUIREMENT]
UID: GSSC-BLLR-187
TITLE: User Update Home Address line 1
STATEMENT: >>>
The GSSC Website Unified Backend SHALL store a posted Home Address line 1 when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-189
TITLE: User Update Home Address line 2
STATEMENT: >>>
The GSSC Website Unified Backend SHALL store a posted Home Address line 2 when the caller is an administrator, when the cuid is the caller's own cuid and that user is not an administrator, or when the caller is a user moderator and the user identified by the cuid is not an administrator. An included Home Address line 2 of "" clears the Home Address line 2.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-190
TITLE: User Update Home Address line 3
STATEMENT: >>>
The GSSC Website Unified Backend SHALL store a posted Home Address line 3 when the caller is an administrator, when the cuid is the caller's own cuid and that user is not an administrator, or when the caller is a user moderator and the user identified by the cuid is not an administrator. An included Home Address line 3 of "" clears the Home Address line 3.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-191
TITLE: User Update Home Address city
STATEMENT: >>>
The GSSC Website Unified Backend SHALL store a posted Home Address city when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-193
TITLE: User Update Home Address state
STATEMENT: >>>
The GSSC Website Unified Backend SHALL store a posted Home Address state when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-195
TITLE: User Update Home Address zip code
STATEMENT: >>>
The GSSC Website Unified Backend SHALL store a posted Home Address zip code when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-197
TITLE: User Update Home Address zip extension
STATEMENT: >>>
The GSSC Website Unified Backend SHALL store a posted Home Address zip extension when the caller is an administrator, when the cuid is the caller's own cuid and that user is not an administrator, or when the caller is a user moderator and the user identified by the cuid is not an administrator. An included Home Address zip extension of "" clears the Home Address zip extension.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-198
TITLE: User Update Mailing Address line 1
STATEMENT: >>>
The GSSC Website Unified Backend SHALL store a posted Mailing Address line 1 when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-200
TITLE: User Update Mailing Address line 2
STATEMENT: >>>
The GSSC Website Unified Backend SHALL store a posted Mailing Address line 2 when the caller is an administrator, when the cuid is the caller's own cuid and that user is not an administrator, or when the caller is a user moderator and the user identified by the cuid is not an administrator. An included Mailing Address line 2 of "" clears the Mailing Address line 2.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-201
TITLE: User Update Mailing Address line 3
STATEMENT: >>>
The GSSC Website Unified Backend SHALL store a posted Mailing Address line 3 when the caller is an administrator, when the cuid is the caller's own cuid and that user is not an administrator, or when the caller is a user moderator and the user identified by the cuid is not an administrator. An included Mailing Address line 3 of "" clears the Mailing Address line 3.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-202
TITLE: User Update Mailing Address city
STATEMENT: >>>
The GSSC Website Unified Backend SHALL store a posted Mailing Address city when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-204
TITLE: User Update Mailing Address state
STATEMENT: >>>
The GSSC Website Unified Backend SHALL store a posted Mailing Address state when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-206
TITLE: User Update Mailing Address zip code
STATEMENT: >>>
The GSSC Website Unified Backend SHALL store a posted Mailing Address zip code when the caller is an administrator, when the cuid is the caller's own cuid and that user is not an administrator, or when the caller is a user moderator and the user identified by the cuid is not an administrator.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-208
TITLE: User Update Mailing Address zip extension
STATEMENT: >>>
The GSSC Website Unified Backend SHALL store a posted Mailing Address zip extension when the caller is an administrator, when the cuid is the caller's own cuid and that user is not an administrator, or when the caller is a user moderator and the user identified by the cuid is not an administrator. An included Mailing Address zip extension of "" clears the Mailing Address zip extension.
<<<
RATIONALE: >>>
The member can change this field on that member's own account, and an administrator can change it for any user. A user moderator can change it for a user who is not an administrator. No high-level requirement grants that moderator update.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-209
TITLE: User Update Home Address Display
STATEMENT: >>>
The GSSC Website Unified Backend SHALL store a posted Home Address display of full or redacted when the caller is an administrator, when the cuid is the caller's own cuid and that user is not an administrator, or when the caller is a user moderator and the user identified by the cuid is not an administrator.
<<<
RATIONALE: >>>
The member can set that member's own Home Address display, and an administrator can set it for any user. A user moderator can set it for a user who is not an administrator. The moderator update is derived.
<<<
DERIVED: False
VERIFICATION_METHOD: Test
CHANGE_DRIVER: GSSC5-34
REVIEW_STATUS: Approved
RELATIONS:
- TYPE: Parent
  VALUE: GSSC-BHLR-12
  ROLE: Refines
- TYPE: Parent
  VALUE: GSSC-BHLR-80
  ROLE: Refines

[REQUIREMENT]
UID: GSSC-BLLR-211
TITLE: User Update Secondary Email Display
STATEMENT: >>>
The GSSC Website Unified Backend SHALL store a posted choice to display or not display the Secondary Email when the caller is an administrator, when the cuid is the caller's own cuid and that user is not an administrator, or when the caller is a user moderator and the user identified by the cuid is not an administrator.
<<<
RATIONALE: >>>
The member can set that member's own Secondary Email display. An administrator can set it for any user, and a user moderator can set it for a user who is not an administrator. The moderator update is derived.
<<<
DERIVED: False
VERIFICATION_METHOD: Test
CHANGE_DRIVER: GSSC5-34
REVIEW_STATUS: Approved
RELATIONS:
- TYPE: Parent
  VALUE: GSSC-BHLR-48
  ROLE: Refines

[REQUIREMENT]
UID: GSSC-BLLR-212
TITLE: User Update Secondary Phone Number Display
STATEMENT: >>>
The GSSC Website Unified Backend SHALL store a posted choice to display or not display the Secondary Phone Number when the caller is an administrator, when the cuid is the caller's own cuid and that user is not an administrator, or when the caller is a user moderator and the user identified by the cuid is not an administrator.
<<<
RATIONALE: >>>
The member can set that member's own Secondary Phone Number display. An administrator can set it for any user, and a user moderator can set it for a user who is not an administrator. The moderator update is derived.
<<<
DERIVED: False
VERIFICATION_METHOD: Test
CHANGE_DRIVER: GSSC5-34
REVIEW_STATUS: Approved
RELATIONS:
- TYPE: Parent
  VALUE: GSSC-BHLR-49
  ROLE: Refines

[REQUIREMENT]
UID: GSSC-BLLR-65
TITLE: Username Update
STATEMENT: >>>
The GSSC Website Unified Backend SHALL store a posted Username when the caller is an administrator, when the cuid is the caller's own cuid and that user is not an administrator, or when the caller is a user moderator and the user identified by the cuid is not an administrator.
<<<
RATIONALE: >>>
The current member, a user moderator, and an administrator can change the Username of a user they are allowed to update. No high-level requirement says a member can change it.
<<<
DERIVED: True
VERIFICATION_METHOD: Test
CHANGE_DRIVER: GSSC5-34
REVIEW_STATUS: Approved

[REQUIREMENT]
UID: GSSC-BLLR-61
TITLE: Permission Update
STATEMENT: >>>
The GSSC Website Unified Backend SHALL store a posted is administrator value of true or false when the caller is an administrator.
<<<
RATIONALE: >>>
An administrator can set is administrator to true or false.
<<<
DERIVED: False
VERIFICATION_METHOD: Test
CHANGE_DRIVER: GSSC5-34
REVIEW_STATUS: Approved
RELATIONS:
- TYPE: Parent
  VALUE: GSSC-BHLR-81
  ROLE: Refines
- TYPE: Parent
  VALUE: GSSC-BHLR-169
  ROLE: Refines

[REQUIREMENT]
UID: GSSC-BLLR-220
TITLE: User is user moderator Update
STATEMENT: >>>
The GSSC Website Unified Backend SHALL store a posted is user moderator value of true or false when the caller is an administrator.
<<<
RATIONALE: >>>
An administrator can set is user moderator to true or false.
<<<
DERIVED: False
VERIFICATION_METHOD: Test
CHANGE_DRIVER: GSSC5-34
REVIEW_STATUS: Approved
RELATIONS:
- TYPE: Parent
  VALUE: GSSC-BHLR-81
  ROLE: Refines
- TYPE: Parent
  VALUE: GSSC-BHLR-169
  ROLE: Refines

[REQUIREMENT]
UID: GSSC-BLLR-66
TITLE: Membership Status Update
STATEMENT: >>>
The GSSC Website Unified Backend SHALL store a posted Membership Status when the caller is not the user identified by the cuid and the caller is an administrator. The user update also stores that status when the caller is a user moderator and that user is not an administrator. An authorized caller clears Membership Status with "".
<<<
RATIONALE: >>>
An administrator can change another user's Membership Status. A user moderator can change it for a user who is not the caller and who is not an administrator. No high-level requirement says who may change Membership Status. The status values remain unnamed.
<<<
DERIVED: True
VERIFICATION_METHOD: Test
CHANGE_DRIVER: GSSC5-34
REVIEW_STATUS: Approved

[REQUIREMENT]
UID: GSSC-BLLR-279
TITLE: Administrator Position Update
STATEMENT: >>>
The GSSC Website Unified Backend SHALL store a posted Position when the caller is an administrator.
<<<
RATIONALE: >>>
An administrator can set any member's Position, including that administrator's own Position.
<<<
DERIVED: False
VERIFICATION_METHOD: Test
CHANGE_DRIVER: GSSC5-36
REVIEW_STATUS: Approved
RELATIONS:
- TYPE: Parent
  VALUE: GSSC-BHLR-86
  ROLE: Refines

[REQUIREMENT]
UID: GSSC-BLLR-280
TITLE: User Moderator Position Update
STATEMENT: >>>
The GSSC Website Unified Backend SHALL store a posted Position when the caller is a user moderator and the user identified by the cuid is another member who is not an administrator.
<<<
RATIONALE: >>>
A user moderator can set Position for another member who is not an administrator.
<<<
DERIVED: False
VERIFICATION_METHOD: Test
CHANGE_DRIVER: GSSC5-36
REVIEW_STATUS: Approved
RELATIONS:
- TYPE: Parent
  VALUE: GSSC-BHLR-86
  ROLE: Refines

[REQUIREMENT]
UID: GSSC-BLLR-281
TITLE: Position Clear
STATEMENT: >>>
The GSSC Website Unified Backend SHALL clear the stored Position when an authorized caller posts Position as "".
<<<
RATIONALE: >>>
An empty Position clears the stored value and removes that member from the leadership list.
<<<
DERIVED: False
VERIFICATION_METHOD: Test
CHANGE_DRIVER: GSSC5-36
REVIEW_STATUS: Approved
RELATIONS:
- TYPE: Parent
  VALUE: GSSC-BHLR-110
  ROLE: Refines

[[/SECTION]]

[[SECTION]]
UID: GSSC-BLLR-USER-POST-FAILURES
TITLE: Failure Cases

[REQUIREMENT]
UID: GSSC-BLLR-56
TITLE: User Update Missing Login Token
STATEMENT: >>>
The GSSC Website Unified Backend SHALL forbid the user update when the Login Token in the HTTP cookie is missing.
<<<
RATIONALE: >>>
A missing Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-36
  ROLE: Refines

[REQUIREMENT]
UID: GSSC-BLLR-166
TITLE: User Update Unknown Login Token
STATEMENT: >>>
The GSSC Website Unified Backend SHALL forbid the user update when the Login Token in the HTTP cookie is unknown.
<<<
RATIONALE: >>>
An unknown Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-36
  ROLE: Refines

[REQUIREMENT]
UID: GSSC-BLLR-167
TITLE: User Update Logged-Out Login Token
STATEMENT: >>>
The GSSC Website Unified Backend SHALL forbid the user update when the Login Token in the HTTP cookie has been logged out.
<<<
RATIONALE: >>>
A logged-out Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-36
  ROLE: Refines

[REQUIREMENT]
UID: GSSC-BLLR-168
TITLE: User Update Expired Login Token
STATEMENT: >>>
The GSSC Website Unified Backend SHALL forbid the user update when the Login Token in the HTTP cookie has expired.
<<<
RATIONALE: >>>
An expired Login Token is not a current login. The failure does not say which check failed.
<<<
DERIVED: False
VERIFICATION_METHOD: Test
CHANGE_DRIVER: GSSC5-34, GSSC5-48
REVIEW_STATUS: Approved
RELATIONS:
- TYPE: Parent
  VALUE: GSSC-BHLR-36
  ROLE: Refines

[REQUIREMENT]
UID: GSSC-BLLR-57
TITLE: User Update Not Found
STATEMENT: >>>
The GSSC Website Unified Backend SHALL report the user not found when the user update names a cuid that no user has.
<<<
RATIONALE: >>>
A cuid that belongs to no user is a missing record. The test binds this report to HTTP 404.
<<<
DERIVED: True
VERIFICATION_METHOD: Test
CHANGE_DRIVER: GSSC5-34
REVIEW_STATUS: Approved

[REQUIREMENT]
UID: GSSC-BLLR-59
TITLE: is administrator User Update
STATEMENT: >>>
The GSSC Website Unified Backend SHALL forbid the user update when the caller is not an administrator and the user identified by the cuid is an administrator, and the backend writes nothing.
<<<
RATIONALE: >>>
A user who is an administrator can be changed only by an administrator. A user moderator is forbidden from updating an administrator, and the backend writes nothing.
<<<
DERIVED: False
VERIFICATION_METHOD: Test
CHANGE_DRIVER: GSSC5-34
REVIEW_STATUS: Approved
RELATIONS:
- TYPE: Parent
  VALUE: GSSC-BHLR-60
  ROLE: Refines

[REQUIREMENT]
UID: GSSC-BLLR-171
TITLE: User Update Forbidden
STATEMENT: >>>
The GSSC Website Unified Backend SHALL forbid the user update when the cuid is not the caller's own cuid and the caller is not a user moderator, and the backend writes nothing.
<<<
RATIONALE: >>>
A caller who is not a user moderator and is not the identified user is forbidden from updating that user. An administrator is a user moderator.
<<<
DERIVED: False
VERIFICATION_METHOD: Test
CHANGE_DRIVER: >>>
GSSC5-34
GSSC5-36
<<<
REVIEW_STATUS: Approved
RELATIONS:
- TYPE: Parent
  VALUE: GSSC-BHLR-36
  ROLE: Refines

[REQUIREMENT]
UID: GSSC-BLLR-173
TITLE: User Update Cuid
STATEMENT: >>>
The GSSC Website Unified Backend SHALL invalidate the user update when the request includes a cuid, and the backend writes nothing.
<<<
RATIONALE: >>>
The cuid in the path identifies the user. A cuid in the update body is an invalid field, and the backend writes nothing.
<<<
DERIVED: True
VERIFICATION_METHOD: Test
CHANGE_DRIVER: GSSC5-34
REVIEW_STATUS: Approved

[REQUIREMENT]
UID: GSSC-BLLR-175
TITLE: User Update First Name Empty
STATEMENT: >>>
The GSSC Website Unified Backend SHALL invalidate the user update when an included First Name is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-36
  ROLE: Refines
- TYPE: Parent
  VALUE: GSSC-BHLR-60
  ROLE: Refines

[REQUIREMENT]
UID: GSSC-BLLR-178
TITLE: User Update Last Name Empty
STATEMENT: >>>
The GSSC Website Unified Backend SHALL invalidate the user update when an included Last Name is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-38
  ROLE: Refines
- TYPE: Parent
  VALUE: GSSC-BHLR-62
  ROLE: Refines

[REQUIREMENT]
UID: GSSC-BLLR-180
TITLE: User Update Primary Email Empty
STATEMENT: >>>
The GSSC Website Unified Backend SHALL invalidate the user update when an included Primary Email is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-39
  ROLE: Refines
- TYPE: Parent
  VALUE: GSSC-BHLR-63
  ROLE: Refines

[REQUIREMENT]
UID: GSSC-BLLR-183
TITLE: User Update Primary Phone Number Empty
STATEMENT: >>>
The GSSC Website Unified Backend SHALL invalidate the user update when an included Primary Phone Number is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-41
  ROLE: Refines
- TYPE: Parent
  VALUE: GSSC-BHLR-65
  ROLE: Refines

[REQUIREMENT]
UID: GSSC-BLLR-186
TITLE: User Update Preferred Contact Method Empty
STATEMENT: >>>
The GSSC Website Unified Backend SHALL invalidate the user update when an included Preferred Contact Method is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-43
  ROLE: Refines
- TYPE: Parent
  VALUE: GSSC-BHLR-67
  ROLE: Refines

[REQUIREMENT]
UID: GSSC-BLLR-188
TITLE: User Update Home Address line 1 Empty
STATEMENT: >>>
The GSSC Website Unified Backend SHALL invalidate the user update when an included Home Address line 1 is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-192
TITLE: User Update Home Address city Empty
STATEMENT: >>>
The GSSC Website Unified Backend SHALL invalidate the user update when an included Home Address city is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-194
TITLE: User Update Home Address state Empty
STATEMENT: >>>
The GSSC Website Unified Backend SHALL invalidate the user update when an included Home Address state is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-196
TITLE: User Update Home Address zip code Empty
STATEMENT: >>>
The GSSC Website Unified Backend SHALL invalidate the user update when an included Home Address zip code is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-199
TITLE: User Update Mailing Address line 1 Empty
STATEMENT: >>>
The GSSC Website Unified Backend SHALL invalidate the user update when an included Mailing Address line 1 is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-203
TITLE: User Update Mailing Address city Empty
STATEMENT: >>>
The GSSC Website Unified Backend SHALL invalidate the user update when an included Mailing Address city is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-205
TITLE: User Update Mailing Address state Empty
STATEMENT: >>>
The GSSC Website Unified Backend SHALL invalidate the user update when an included Mailing Address state is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-207
TITLE: User Update Mailing Address zip code Empty
STATEMENT: >>>
The GSSC Website Unified Backend SHALL invalidate the user update when an included Mailing Address zip code is "" for a user other than the permanent admin account, and the backend writes nothing.
<<<
RATIONALE: >>>
This required field stays non-empty. The permanent admin account may store it empty. An empty value for any other user invalidates the update, and the backend writes nothing.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-210
TITLE: User Update Home Address Display Value
STATEMENT: >>>
The GSSC Website Unified Backend SHALL invalidate the user update when a posted Home Address display is neither full nor redacted, and the backend writes nothing.
<<<
RATIONALE: >>>
The Home Address display is full or redacted. Any other posted value invalidates the update.
<<<
DERIVED: False
VERIFICATION_METHOD: Test
CHANGE_DRIVER: GSSC5-34
REVIEW_STATUS: Approved
RELATIONS:
- TYPE: Parent
  VALUE: GSSC-BHLR-12
  ROLE: Refines
- TYPE: Parent
  VALUE: GSSC-BHLR-80
  ROLE: Refines

[REQUIREMENT]
UID: GSSC-BLLR-213
TITLE: User Update Home Address zip code Shape
STATEMENT: >>>
The GSSC Website Unified Backend SHALL invalidate the user update when a posted Home Address zip code is not empty and is not five digits, and the backend writes nothing.
<<<
RATIONALE: >>>
A zip code is five digits. A non-empty value of any other shape invalidates the update, and the backend writes nothing.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-214
TITLE: User Update Mailing Address zip code Shape
STATEMENT: >>>
The GSSC Website Unified Backend SHALL invalidate the user update when a posted Mailing Address zip code is not empty and is not five digits, and the backend writes nothing.
<<<
RATIONALE: >>>
A zip code is five digits. A non-empty value of any other shape invalidates the update, and the backend writes nothing.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-215
TITLE: User Update Home Address zip extension Shape
STATEMENT: >>>
The GSSC Website Unified Backend SHALL invalidate the user update when a posted Home Address zip extension is not empty and is not four digits, and the backend writes nothing.
<<<
RATIONALE: >>>
A zip extension is four digits when it is present. A non-empty value of any other shape invalidates the update, and the backend writes nothing.
<<<
DERIVED: False
VERIFICATION_METHOD: Test
CHANGE_DRIVER: GSSC5-34
REVIEW_STATUS: Approved
RELATIONS:
- TYPE: Parent
  VALUE: GSSC-BHLR-44
  ROLE: Refines
- TYPE: Parent
  VALUE: GSSC-BHLR-68
  ROLE: Refines

[REQUIREMENT]
UID: GSSC-BLLR-216
TITLE: User Update Mailing Address zip extension Shape
STATEMENT: >>>
The GSSC Website Unified Backend SHALL invalidate the user update when a posted Mailing Address zip extension is not empty and is not four digits, and the backend writes nothing.
<<<
RATIONALE: >>>
A zip extension is four digits when it is present. A non-empty value of any other shape invalidates the update, and the backend writes nothing.
<<<
DERIVED: False
VERIFICATION_METHOD: Test
CHANGE_DRIVER: GSSC5-34
REVIEW_STATUS: Approved
RELATIONS:
- TYPE: Parent
  VALUE: GSSC-BHLR-45
  ROLE: Refines
- TYPE: Parent
  VALUE: GSSC-BHLR-69
  ROLE: Refines

[REQUIREMENT]
UID: GSSC-BLLR-217
TITLE: User Update Preferred Contact Method Value
STATEMENT: >>>
The GSSC Website Unified Backend SHALL invalidate the user update when a posted Preferred Contact Method for a user other than the permanent admin account is not Email, Phone, or None, and the backend writes nothing.
<<<
RATIONALE: >>>
The Preferred Contact Method is Email, Phone, or None. The permanent admin account may store it empty. Any other posted value invalidates the update, and the backend writes nothing.
<<<
DERIVED: False
VERIFICATION_METHOD: Test
CHANGE_DRIVER: GSSC5-34
REVIEW_STATUS: Approved
RELATIONS:
- TYPE: Parent
  VALUE: GSSC-BHLR-43
  ROLE: Refines
- TYPE: Parent
  VALUE: GSSC-BHLR-67
  ROLE: Refines
- TYPE: Parent
  VALUE: GSSC-BHLR-11
  ROLE: Refines

[REQUIREMENT]
UID: GSSC-BLLR-218
TITLE: Username Empty
STATEMENT: >>>
The GSSC Website Unified Backend SHALL invalidate the user update when an included Username is "", and the backend writes nothing.
<<<
RATIONALE: >>>
Every user has a Username. An empty Username invalidates the update, and the backend writes nothing.
<<<
DERIVED: True
VERIFICATION_METHOD: Test
CHANGE_DRIVER: GSSC5-34
REVIEW_STATUS: Approved

[REQUIREMENT]
UID: GSSC-BLLR-219
TITLE: Username Already Stored
STATEMENT: >>>
The GSSC Website Unified Backend SHALL invalidate the user update when the posted Username is already stored for another user, and the backend writes nothing.
<<<
RATIONALE: >>>
Each Username belongs to one user. An update that would give a second user that Username is invalidated, and the backend writes nothing.
<<<
DERIVED: True
VERIFICATION_METHOD: Test
CHANGE_DRIVER: GSSC5-34
REVIEW_STATUS: Approved

[REQUIREMENT]
UID: GSSC-BLLR-63
TITLE: Primary Email Still Unique
STATEMENT: >>>
The GSSC Website Unified Backend SHALL invalidate the user update when the posted Primary Email is already stored for another user. The backend writes nothing.
<<<
RATIONALE: >>>
Each Primary Email belongs to one user. An update that would give a second user that Primary Email is invalidated, and the stored values stay as they are.
<<<
DERIVED: False
VERIFICATION_METHOD: Test
CHANGE_DRIVER: GSSC5-34
REVIEW_STATUS: Approved
RELATIONS:
- TYPE: Parent
  VALUE: GSSC-BHLR-101
  ROLE: Refines

[REQUIREMENT]
UID: GSSC-BLLR-221
TITLE: Permission Update Forbidden
STATEMENT: >>>
The GSSC Website Unified Backend SHALL forbid the user update when the caller is not an administrator and the request includes is administrator, and the backend writes nothing.
<<<
RATIONALE: >>>
A caller who is not an administrator is forbidden from changing is administrator, and the backend writes nothing.
<<<
DERIVED: False
VERIFICATION_METHOD: Test
CHANGE_DRIVER: GSSC5-34
REVIEW_STATUS: Approved
RELATIONS:
- TYPE: Parent
  VALUE: GSSC-BHLR-81
  ROLE: Refines
- TYPE: Parent
  VALUE: GSSC-BHLR-169
  ROLE: Refines

[REQUIREMENT]
UID: GSSC-BLLR-222
TITLE: User is user moderator Update Forbidden
STATEMENT: >>>
The GSSC Website Unified Backend SHALL forbid the user update when the caller is not an administrator and the request includes is user moderator, and the backend writes nothing.
<<<
RATIONALE: >>>
A caller who is not an administrator is forbidden from changing is user moderator, and the backend writes nothing.
<<<
DERIVED: False
VERIFICATION_METHOD: Test
CHANGE_DRIVER: GSSC5-34
REVIEW_STATUS: Approved
RELATIONS:
- TYPE: Parent
  VALUE: GSSC-BHLR-81
  ROLE: Refines
- TYPE: Parent
  VALUE: GSSC-BHLR-169
  ROLE: Refines

[REQUIREMENT]
UID: GSSC-BLLR-223
TITLE: Own Membership Status Update
STATEMENT: >>>
The GSSC Website Unified Backend SHALL invalidate the user update when the cuid is the caller's own user and the request includes Membership Status, and the backend writes nothing.
<<<
RATIONALE: >>>
A member can see their own Membership Status and cannot change it. Including it on that member's own update invalidates the update, and the backend writes nothing.
<<<
DERIVED: True
VERIFICATION_METHOD: Test
CHANGE_DRIVER: GSSC5-34
REVIEW_STATUS: Approved

[REQUIREMENT]
UID: GSSC-BLLR-282
TITLE: Own Position Update
STATEMENT: >>>
The GSSC Website Unified Backend SHALL invalidate the user update when the cuid is the caller's own user, the caller is not an administrator, and the request includes Position, and the backend writes nothing.
<<<
RATIONALE: >>>
A member's own Position is view-only unless that member is an administrator. Including Position on that member's own update invalidates the update, and the backend writes nothing.
<<<
DERIVED: False
VERIFICATION_METHOD: Test
CHANGE_DRIVER: GSSC5-36
REVIEW_STATUS: Approved
RELATIONS:
- TYPE: Parent
  VALUE: GSSC-BHLR-84
  ROLE: Refines
- TYPE: Parent
  VALUE: GSSC-BHLR-86
  ROLE: Refines

[REQUIREMENT]
UID: GSSC-BLLR-62
TITLE: Password Hash Unchanged
STATEMENT: >>>
The GSSC Website Unified Backend SHALL invalidate the user update when the request includes the password hash, and the backend writes nothing. The stored password hash remains the current hash.
<<<
RATIONALE: >>>
Password replacement uses the password change and recovery transactions. No high-level requirement requires invalidating a user update that includes the password hash, so that invalidation is derived.
<<<
DERIVED: True
VERIFICATION_METHOD: Test
CHANGE_DRIVER: GSSC5-34, GSSC5-35
REVIEW_STATUS: Approved

[[/SECTION]]

[[/SECTION]]

[[/SECTION]]

[[/SECTION]]

[[/SECTION]]

[[SECTION]]
UID: GSSC-BLLR-LEADERSHIP
TITLE: /leadership

[REQUIREMENT]
UID: GSSC-BLLR-283
TITLE: Leadership List
STATEMENT: >>>
The GSSC Website Unified Backend SHALL let an unauthenticated caller retrieve the leadership list.
<<<
RATIONALE: >>>
The public leadership list is available without a login.
<<<
DERIVED: False
VERIFICATION_METHOD: Test
CHANGE_DRIVER: GSSC5-36
REVIEW_STATUS: Approved
RELATIONS:
- TYPE: Parent
  VALUE: GSSC-BHLR-88
  ROLE: Refines
- TYPE: Parent
  VALUE: GSSC-BHLR-171
  ROLE: Refines

[REQUIREMENT]
UID: GSSC-BLLR-284
TITLE: Leadership List Populated Position
STATEMENT: >>>
The GSSC Website Unified Backend SHALL include in the leadership list each stored user whose Position is populated.
<<<
RATIONALE: >>>
Leaders are the members whose Position is populated. A member with an empty Position is left off the list.
<<<
DERIVED: False
VERIFICATION_METHOD: Test
CHANGE_DRIVER: GSSC5-36
REVIEW_STATUS: Approved
RELATIONS:
- TYPE: Parent
  VALUE: GSSC-BHLR-88
  ROLE: Refines
- TYPE: Parent
  VALUE: GSSC-BHLR-95
  ROLE: Refines

[REQUIREMENT]
UID: GSSC-BLLR-285
TITLE: Leadership Entry Position
STATEMENT: >>>
The GSSC Website Unified Backend SHALL return the Position in each leadership list entry.
<<<
RATIONALE: >>>
The public role of a leader is that leader's Position.
<<<
DERIVED: False
VERIFICATION_METHOD: Test
CHANGE_DRIVER: GSSC5-36
REVIEW_STATUS: Approved
RELATIONS:
- TYPE: Parent
  VALUE: GSSC-BHLR-89
  ROLE: Refines
- TYPE: Parent
  VALUE: GSSC-BHLR-95
  ROLE: Refines

[REQUIREMENT]
UID: GSSC-BLLR-286
TITLE: Leadership Entry First Name
STATEMENT: >>>
The GSSC Website Unified Backend SHALL return the First Name in each leadership list entry.
<<<
RATIONALE: >>>
The public can see the First Name of each leader.
<<<
DERIVED: False
VERIFICATION_METHOD: Test
CHANGE_DRIVER: GSSC5-36
REVIEW_STATUS: Approved
RELATIONS:
- TYPE: Parent
  VALUE: GSSC-BHLR-90
  ROLE: Refines

[REQUIREMENT]
UID: GSSC-BLLR-287
TITLE: Leadership Entry Last Name
STATEMENT: >>>
The GSSC Website Unified Backend SHALL return the Last Name in each leadership list entry.
<<<
RATIONALE: >>>
The public can see the Last Name of each leader.
<<<
DERIVED: False
VERIFICATION_METHOD: Test
CHANGE_DRIVER: GSSC5-36
REVIEW_STATUS: Approved
RELATIONS:
- TYPE: Parent
  VALUE: GSSC-BHLR-91
  ROLE: Refines

[REQUIREMENT]
UID: GSSC-BLLR-288
TITLE: Leadership Entry Account Photo
STATEMENT: >>>
The GSSC Website Unified Backend SHALL return the Account Photo in a leadership list entry when that Account Photo is stored.
<<<
RATIONALE: >>>
The public can see the Account Photo of a leader when the account holds one.
<<<
DERIVED: False
VERIFICATION_METHOD: Test
CHANGE_DRIVER: GSSC5-36
REVIEW_STATUS: Approved
RELATIONS:
- TYPE: Parent
  VALUE: GSSC-BHLR-94
  ROLE: Refines

[REQUIREMENT]
UID: GSSC-BLLR-289
TITLE: Leadership Entry Primary Email
STATEMENT: >>>
The GSSC Website Unified Backend SHALL return the Primary Email in a leadership list entry when that leader's Preferred Contact Method is Email.
<<<
RATIONALE: >>>
The public receives a leader's Primary Email when Email is the preferred contact method.
<<<
DERIVED: False
VERIFICATION_METHOD: Test
CHANGE_DRIVER: GSSC5-36
REVIEW_STATUS: Approved
RELATIONS:
- TYPE: Parent
  VALUE: GSSC-BHLR-92
  ROLE: Refines

[REQUIREMENT]
UID: GSSC-BLLR-290
TITLE: Leadership Entry Primary Phone Number
STATEMENT: >>>
The GSSC Website Unified Backend SHALL return the Primary Phone Number in a leadership list entry when that leader's Preferred Contact Method is Phone.
<<<
RATIONALE: >>>
The public receives a leader's Primary Phone Number when Phone is the preferred contact method.
<<<
DERIVED: False
VERIFICATION_METHOD: Test
CHANGE_DRIVER: GSSC5-36
REVIEW_STATUS: Approved
RELATIONS:
- TYPE: Parent
  VALUE: GSSC-BHLR-93
  ROLE: Refines

[REQUIREMENT]
UID: GSSC-BLLR-291
TITLE: Leadership Entry Preferred Contact Method
STATEMENT: >>>
The GSSC Website Unified Backend SHALL return the Preferred Contact Method in each leadership list entry.
<<<
RATIONALE: >>>
The type of the preferred contact is that member's Preferred Contact Method.
<<<
DERIVED: False
VERIFICATION_METHOD: Test
CHANGE_DRIVER: GSSC5-36
REVIEW_STATUS: Approved
RELATIONS:
- TYPE: Parent
  VALUE: GSSC-BHLR-171
  ROLE: Refines

[[/SECTION]]

[[SECTION]]
UID: GSSC-BLLR-KVS
TITLE: /kvs

[[SECTION]]
UID: GSSC-BLLR-KVS-GET
TITLE: GET Key

[REQUIREMENT]
UID: GSSC-BLLR-293
TITLE: Key-Value Public Read
STATEMENT: >>>
The GSSC Website Unified Backend SHALL let an unauthenticated caller retrieve a stored key-value entry by key.
<<<
RATIONALE: >>>
The public reads global website data from the key-value store without a login.
<<<
DERIVED: False
VERIFICATION_METHOD: Test
CHANGE_DRIVER: GSSC5-43
REVIEW_STATUS: Approved
RELATIONS:
- TYPE: Parent
  VALUE: GSSC-BHLR-180
  ROLE: Refines

[REQUIREMENT]
UID: GSSC-BLLR-294
TITLE: Key-Value Entry Contents
STATEMENT: >>>
The GSSC Website Unified Backend SHALL return the key and the value of the stored key-value entry.
<<<
RATIONALE: >>>
The caller receives the requested key with its stored value.
<<<
DERIVED: False
VERIFICATION_METHOD: Test
CHANGE_DRIVER: GSSC5-43
REVIEW_STATUS: Approved
RELATIONS:
- TYPE: Parent
  VALUE: GSSC-BHLR-180
  ROLE: Refines

[REQUIREMENT]
UID: GSSC-BLLR-295
TITLE: Key-Value Entry Not Found
STATEMENT: >>>
The GSSC Website Unified Backend SHALL report not found when the key-value store has no entry for the requested key.
<<<
RATIONALE: >>>
A missing key is a missing record. The test binds this report to HTTP 404.
<<<
DERIVED: False
VERIFICATION_METHOD: Test
CHANGE_DRIVER: GSSC5-43
REVIEW_STATUS: Approved
RELATIONS:
- TYPE: Parent
  VALUE: GSSC-BHLR-180
  ROLE: Refines

[[/SECTION]]

[[SECTION]]
UID: GSSC-BLLR-KVS-POST
TITLE: POST Key

[REQUIREMENT]
UID: GSSC-BLLR-296
TITLE: Key-Value Entry Upsert
STATEMENT: >>>
The GSSC Website Unified Backend SHALL create or replace the key-value entry for the key in the path when an administrator authenticated by the Login Token HTTP cookie supplies a value in the request body.
<<<
RATIONALE: >>>
An administrator creates a new entry or replaces the value of an existing entry. The Login Token is taken from the HTTP cookie.
<<<
DERIVED: False
VERIFICATION_METHOD: Test
CHANGE_DRIVER: GSSC5-43
REVIEW_STATUS: Approved
RELATIONS:
- TYPE: Parent
  VALUE: GSSC-BHLR-181
  ROLE: Refines

[REQUIREMENT]
UID: GSSC-BLLR-297
TITLE: Key-Value Upsert Login Token Required
STATEMENT: >>>
The GSSC Website Unified Backend SHALL forbid a key-value upsert when the Login Token HTTP cookie is missing or is not a valid Login Token, and the backend writes nothing.
<<<
RATIONALE: >>>
Only a logged-in administrator may create or replace a key-value entry. The Login Token is taken from the HTTP cookie.
<<<
DERIVED: False
VERIFICATION_METHOD: Test
CHANGE_DRIVER: GSSC5-43
REVIEW_STATUS: Approved
RELATIONS:
- TYPE: Parent
  VALUE: GSSC-BHLR-181
  ROLE: Refines

[REQUIREMENT]
UID: GSSC-BLLR-298
TITLE: Key-Value Upsert Privilege
STATEMENT: >>>
The GSSC Website Unified Backend SHALL complete a key-value upsert when the Login Token from the HTTP cookie belongs to a caller who is an administrator.
<<<
RATIONALE: >>>
Creating or replacing a key-value entry is limited to an administrator. The Login Token is taken from the HTTP cookie.
<<<
DERIVED: False
VERIFICATION_METHOD: Test
CHANGE_DRIVER: GSSC5-43
REVIEW_STATUS: Approved
RELATIONS:
- TYPE: Parent
  VALUE: GSSC-BHLR-181
  ROLE: Refines

[REQUIREMENT]
UID: GSSC-BLLR-299
TITLE: Key-Value Upsert Forbidden
STATEMENT: >>>
The GSSC Website Unified Backend SHALL forbid a key-value upsert when the caller is not an administrator, and the backend writes nothing.
<<<
RATIONALE: >>>
A caller who is not an administrator cannot create or replace a key-value entry.
<<<
DERIVED: False
VERIFICATION_METHOD: Test
CHANGE_DRIVER: GSSC5-43
REVIEW_STATUS: Approved
RELATIONS:
- TYPE: Parent
  VALUE: GSSC-BHLR-181
  ROLE: Refines

[REQUIREMENT]
UID: GSSC-BLLR-300
TITLE: Key-Value Upsert Value Required
STATEMENT: >>>
The GSSC Website Unified Backend SHALL invalidate a key-value upsert when the request omits a string value, and the backend writes nothing.
<<<
RATIONALE: >>>
A key-value upsert requires a string value for that key.
<<<
DERIVED: True
VERIFICATION_METHOD: Test
CHANGE_DRIVER: GSSC5-43
REVIEW_STATUS: Approved

[[/SECTION]]

[[/SECTION]]

[[SECTION]]
UID: GSSC-BLLR-WEBPAGE-CONTENT
TITLE: Webpage Content

[[SECTION]]
UID: GSSC-BLLR-GENERIC-CONTENT
TITLE: Generic Content

[[SECTION]]
UID: GSSC-BLLR-SECTIONS-CATEGORY
TITLE: Sections

[[SECTION]]
UID: GSSC-BLLR-SECTIONS-COLLECTION
TITLE: /sections

[[SECTION]]
UID: GSSC-BLLR-SECTIONS-COLLECTION-GET
TITLE: GET

[REQUIREMENT]
UID: GSSC-BLLR-320
TITLE: Public Section List
STATEMENT: >>>
The GSSC Website Unified Backend SHALL return only public sections when listing sections without a valid Login Token.
<<<
RATIONALE: >>>
Unauthenticated callers see the public catalog only.
<<<
DERIVED: False
VERIFICATION_METHOD: Test
CHANGE_DRIVER: GSSC5-37
REVIEW_STATUS: Approved
RELATIONS:
- TYPE: Parent
  VALUE: GSSC-BHLR-135
  ROLE: Refines

[REQUIREMENT]
UID: GSSC-BLLR-321
TITLE: Authenticated Section List
STATEMENT: >>>
The GSSC Website Unified Backend SHALL return public and members-only sections when listing sections for a logged-in member.
<<<
RATIONALE: >>>
A valid Login Token expands the list to every section.
<<<
DERIVED: False
VERIFICATION_METHOD: Test
CHANGE_DRIVER: GSSC5-37
REVIEW_STATUS: Approved
RELATIONS:
- TYPE: Parent
  VALUE: GSSC-BHLR-137
  ROLE: Refines

[REQUIREMENT]
UID: GSSC-BLLR-322
TITLE: Section List Entry Fields
STATEMENT: >>>
The GSSC Website Unified Backend SHALL include header, body, tags, cuid, and index in each section list entry.
<<<
RATIONALE: >>>
List entries carry the fields needed for page assembly without a second fetch for summary data.
<<<
DERIVED: True
VERIFICATION_METHOD: Test
CHANGE_DRIVER: GSSC5-37
REVIEW_STATUS: Approved
RELATIONS:
- TYPE: Parent
  VALUE: GSSC-BHLR-135
  ROLE: Refines

[REQUIREMENT]
UID: GSSC-BLLR-323
TITLE: Section List Index Order
STATEMENT: >>>
The GSSC Website Unified Backend SHALL order section list results by index ascending.
<<<
RATIONALE: >>>
Index determines order among page data entries that share a page; list order follows that index.
<<<
DERIVED: True
VERIFICATION_METHOD: Test
CHANGE_DRIVER: GSSC5-37
REVIEW_STATUS: Approved
RELATIONS:
- TYPE: Parent
  VALUE: GSSC-BHLR-187
  ROLE: Refines

[REQUIREMENT]
UID: GSSC-BLLR-327
TITLE: Section List Filters
STATEMENT: >>>
The GSSC Website Unified Backend SHALL accept section-list query filters for header, body, tag, cuid, and content, matching header, body, tag, and content as a case-insensitive substring, matching content against the header or the body, and matching cuid exactly.
<<<
RATIONALE: >>>
Filter keys and match rules refine the high-level filter requirement.
<<<
DERIVED: True
VERIFICATION_METHOD: Test
CHANGE_DRIVER: GSSC5-37
REVIEW_STATUS: Approved
RELATIONS:
- TYPE: Parent
  VALUE: GSSC-BHLR-183
  ROLE: Refines

[[/SECTION]]

[[SECTION]]
UID: GSSC-BLLR-SECTIONS-COLLECTION-POST
TITLE: POST

[REQUIREMENT]
UID: GSSC-BLLR-328
TITLE: Section Creation
STATEMENT: >>>
The GSSC Website Unified Backend SHALL create a section from a template for a logged-in member who has create permission on that template, requiring a body and a template cuid, accepting optional header, resources, tags, and index, storing isPublic and permission values from the template, and storing tags as the template tags plus the requested tags.
<<<
RATIONALE: >>>
Creation uses a template for audience and permissions while accepting caller content and order fields.
<<<
DERIVED: True
VERIFICATION_METHOD: Test
CHANGE_DRIVER: GSSC5-37
REVIEW_STATUS: Approved
RELATIONS:
- TYPE: Parent
  VALUE: GSSC-BHLR-184
  ROLE: Refines

[REQUIREMENT]
UID: GSSC-BLLR-329
TITLE: Section Creation Forbidden
STATEMENT: >>>
The GSSC Website Unified Backend SHALL reject section creation without storing a section when the caller lacks create permission on the template.
<<<
RATIONALE: >>>
Create permission on the template gates who may add sections from that category.
<<<
DERIVED: True
VERIFICATION_METHOD: Test
CHANGE_DRIVER: GSSC5-37
REVIEW_STATUS: Approved
RELATIONS:
- TYPE: Parent
  VALUE: GSSC-BHLR-184
  ROLE: Refines

[[/SECTION]]

[[/SECTION]]

[[SECTION]]
UID: GSSC-BLLR-SECTIONS-ITEM
TITLE: /sections/{cuid}

[[SECTION]]
UID: GSSC-BLLR-SECTIONS-ITEM-GET
TITLE: GET

[REQUIREMENT]
UID: GSSC-BLLR-324
TITLE: Public Section Get
STATEMENT: >>>
The GSSC Website Unified Backend SHALL return a public section by cuid in the path to an unauthenticated caller, including header, body, resources, tags, and index.
<<<
RATIONALE: >>>
Path cuid identifies one public section for assembly.
<<<
DERIVED: False
VERIFICATION_METHOD: Test
CHANGE_DRIVER: GSSC5-37
REVIEW_STATUS: Approved
RELATIONS:
- TYPE: Parent
  VALUE: GSSC-BHLR-136
  ROLE: Refines

[REQUIREMENT]
UID: GSSC-BLLR-325
TITLE: Public Section Get Rejects Private
STATEMENT: >>>
The GSSC Website Unified Backend SHALL reject an unauthenticated request for a members-only section by cuid.
<<<
RATIONALE: >>>
Members-only sections stay off the public get path.
<<<
DERIVED: True
VERIFICATION_METHOD: Test
CHANGE_DRIVER: GSSC5-37
REVIEW_STATUS: Approved
RELATIONS:
- TYPE: Parent
  VALUE: GSSC-BHLR-136
  ROLE: Refines

[REQUIREMENT]
UID: GSSC-BLLR-326
TITLE: Authenticated Section Get
STATEMENT: >>>
The GSSC Website Unified Backend SHALL return any section by cuid in the path to a logged-in member, including header, body, resources, tags, and index.
<<<
RATIONALE: >>>
A logged-in member can load public or members-only sections by cuid.
<<<
DERIVED: False
VERIFICATION_METHOD: Test
CHANGE_DRIVER: GSSC5-37
REVIEW_STATUS: Approved
RELATIONS:
- TYPE: Parent
  VALUE: GSSC-BHLR-138
  ROLE: Refines

[[/SECTION]]

[[SECTION]]
UID: GSSC-BLLR-SECTIONS-ITEM-PATCH
TITLE: PATCH

[REQUIREMENT]
UID: GSSC-BLLR-330
TITLE: Section Modification
STATEMENT: >>>
The GSSC Website Unified Backend SHALL accept modification of header, body, resources, tags, and index on a section by a logged-in member who has modify permission on that section.
<<<
RATIONALE: >>>
Modify permission gates content and order updates.
<<<
DERIVED: False
VERIFICATION_METHOD: Test
CHANGE_DRIVER: GSSC5-37
REVIEW_STATUS: Approved
RELATIONS:
- TYPE: Parent
  VALUE: GSSC-BHLR-139
  ROLE: Refines

[REQUIREMENT]
UID: GSSC-BLLR-331
TITLE: Section IsPublic Modification
STATEMENT: >>>
The GSSC Website Unified Backend SHALL accept an isPublic change on a section only when the caller has create, modify, and delete permission on that section.
<<<
RATIONALE: >>>
Audience changes require the full permission set on the entry.
<<<
DERIVED: True
VERIFICATION_METHOD: Test
CHANGE_DRIVER: GSSC5-37
REVIEW_STATUS: Approved
RELATIONS:
- TYPE: Parent
  VALUE: GSSC-BHLR-139
  ROLE: Refines

[[/SECTION]]

[[SECTION]]
UID: GSSC-BLLR-SECTIONS-ITEM-DELETE
TITLE: DELETE

[REQUIREMENT]
UID: GSSC-BLLR-341
TITLE: Section Deletion
STATEMENT: >>>
The GSSC Website Unified Backend SHALL delete a section by cuid for a logged-in member who has delete permission on that section.
<<<
RATIONALE: >>>
Delete permission gates removal of a section identified by path cuid.
<<<
DERIVED: False
VERIFICATION_METHOD: Test
CHANGE_DRIVER: GSSC5-37
REVIEW_STATUS: Approved
RELATIONS:
- TYPE: Parent
  VALUE: GSSC-BHLR-176
  ROLE: Refines

[[/SECTION]]

[[/SECTION]]

[[/SECTION]]

[[SECTION]]
UID: GSSC-BLLR-TEMPLATES-CATEGORY
TITLE: Templates

[[SECTION]]
UID: GSSC-BLLR-TEMPLATES-COLLECTION
TITLE: /templates

[[SECTION]]
UID: GSSC-BLLR-TEMPLATES-COLLECTION-GET
TITLE: GET

[REQUIREMENT]
UID: GSSC-BLLR-333
TITLE: Content Template List
STATEMENT: >>>
The GSSC Website Unified Backend SHALL return each content template's name and cuid when a logged-in member lists templates.
<<<
RATIONALE: >>>
Logged-in members pick a content template when creating an entry.
<<<
DERIVED: True
VERIFICATION_METHOD: Test
CHANGE_DRIVER: GSSC5-37
REVIEW_STATUS: Approved
RELATIONS:
- TYPE: Parent
  VALUE: GSSC-BHLR-186
  ROLE: Refines

[[/SECTION]]

[[SECTION]]
UID: GSSC-BLLR-TEMPLATES-COLLECTION-POST
TITLE: POST

[REQUIREMENT]
UID: GSSC-BLLR-335
TITLE: Content Template Create
STATEMENT: >>>
The GSSC Website Unified Backend SHALL create a content template for an administrator when the request includes a name and isPublic flag, defaulting omitted permission values to 0 and accepting optional tags.
<<<
RATIONALE: >>>
Administrators define content templates used at entry creation.
<<<
DERIVED: True
VERIFICATION_METHOD: Test
CHANGE_DRIVER: GSSC5-37
REVIEW_STATUS: Approved
RELATIONS:
- TYPE: Parent
  VALUE: GSSC-BHLR-186
  ROLE: Refines

[[/SECTION]]

[[/SECTION]]

[[SECTION]]
UID: GSSC-BLLR-TEMPLATES-ITEM
TITLE: /templates/{cuid}

[[SECTION]]
UID: GSSC-BLLR-TEMPLATES-ITEM-GET
TITLE: GET

[REQUIREMENT]
UID: GSSC-BLLR-334
TITLE: Content Template Get
STATEMENT: >>>
The GSSC Website Unified Backend SHALL return a content template's name, isPublic flag, tags, and permission values to an administrator by template cuid in the path.
<<<
RATIONALE: >>>
Administrators inspect content template defaults before managing them.
<<<
DERIVED: True
VERIFICATION_METHOD: Test
CHANGE_DRIVER: GSSC5-37
REVIEW_STATUS: Approved
RELATIONS:
- TYPE: Parent
  VALUE: GSSC-BHLR-186
  ROLE: Refines

[[/SECTION]]

[[SECTION]]
UID: GSSC-BLLR-TEMPLATES-ITEM-PATCH
TITLE: PATCH

[REQUIREMENT]
UID: GSSC-BLLR-336
TITLE: Content Template Modify
STATEMENT: >>>
The GSSC Website Unified Backend SHALL accept administrator modification of a content template's isPublic flag and permission values by cuid while leaving omitted values, the name, and the tags unchanged.
<<<
RATIONALE: >>>
Administrators adjust audience and permissions without renaming or retagging in this operation.
<<<
DERIVED: True
VERIFICATION_METHOD: Test
CHANGE_DRIVER: GSSC5-37
REVIEW_STATUS: Approved
RELATIONS:
- TYPE: Parent
  VALUE: GSSC-BHLR-186
  ROLE: Refines

[[/SECTION]]

[[SECTION]]
UID: GSSC-BLLR-TEMPLATES-ITEM-DELETE
TITLE: DELETE

[REQUIREMENT]
UID: GSSC-BLLR-337
TITLE: Content Template Delete
STATEMENT: >>>
The GSSC Website Unified Backend SHALL delete a content template by cuid when the caller is an administrator.
<<<
RATIONALE: >>>
Administrators remove unused content templates.
<<<
DERIVED: True
VERIFICATION_METHOD: Test
CHANGE_DRIVER: GSSC5-37
REVIEW_STATUS: Approved
RELATIONS:
- TYPE: Parent
  VALUE: GSSC-BHLR-186
  ROLE: Refines

[[/SECTION]]

[[/SECTION]]

[[/SECTION]]

[[SECTION]]
UID: GSSC-BLLR-CONTENT-ADMIN-PERMISSIONS
TITLE: Administrator Permissions

[REQUIREMENT]
UID: GSSC-BLLR-332
TITLE: Administrator Section Permissions
STATEMENT: >>>
The GSSC Website Unified Backend SHALL treat an administrator as having create, modify, and delete permission on every section and every content template.
<<<
RATIONALE: >>>
Administrators retain full control over page data entries and templates.
<<<
DERIVED: True
VERIFICATION_METHOD: Test
CHANGE_DRIVER: GSSC5-37
REVIEW_STATUS: Approved
RELATIONS:
- TYPE: Parent
  VALUE: GSSC-BHLR-185
  ROLE: Refines

[[/SECTION]]

[[/SECTION]]

[[SECTION]]
UID: GSSC-BLLR-RESEARCH-TOOLS-CATEGORY
TITLE: Research Tools

[[SECTION]]
UID: GSSC-BLLR-RESEARCH-TOOLS-COLLECTION
TITLE: /research-tools

[[SECTION]]
UID: GSSC-BLLR-RESEARCH-TOOLS-COLLECTION-GET
TITLE: GET

[REQUIREMENT]
UID: GSSC-BLLR-345
TITLE: Research Tools List
STATEMENT: >>>
The GSSC Website Unified Backend SHALL return each research tool's cuid, title, and reference link when listing research tools.
<<<
RATIONALE: >>>
The public research tools page assembles its hyperlink grid from this list.
<<<
DERIVED: False
VERIFICATION_METHOD: Test
CHANGE_DRIVER: GSSC5-18
REVIEW_STATUS: Changed
RELATIONS:
- TYPE: Parent
  VALUE: GSSC-BHLR-188
  ROLE: Refines

[[/SECTION]]

[[SECTION]]
UID: GSSC-BLLR-RESEARCH-TOOLS-COLLECTION-POST
TITLE: POST

[REQUIREMENT]
UID: GSSC-BLLR-346
TITLE: Research Tool Creation
STATEMENT: >>>
The GSSC Website Unified Backend SHALL create a research tool for a logged-in member who is a tool editor or an administrator, requiring a title and a reference link, and returning the created tool's cuid, title, and reference link.
<<<
RATIONALE: >>>
Authorized editors add tools with the fields the public list presents.
<<<
DERIVED: False
VERIFICATION_METHOD: Test
CHANGE_DRIVER: GSSC5-18
REVIEW_STATUS: Changed
RELATIONS:
- TYPE: Parent
  VALUE: GSSC-BHLR-190
  ROLE: Refines

[REQUIREMENT]
UID: GSSC-BLLR-350
TITLE: Research Tool Creation Forbidden
STATEMENT: >>>
The GSSC Website Unified Backend SHALL reject research tool creation without storing a research tool when the caller is not a tool editor and is not an administrator.
<<<
RATIONALE: >>>
Only tool editors and administrators may add research tools.
<<<
DERIVED: False
VERIFICATION_METHOD: Test
CHANGE_DRIVER: GSSC5-18
REVIEW_STATUS: Changed
RELATIONS:
- TYPE: Parent
  VALUE: GSSC-BHLR-190
  ROLE: Refines

[[/SECTION]]

[[/SECTION]]

[[SECTION]]
UID: GSSC-BLLR-RESEARCH-TOOLS-ITEM
TITLE: /research-tools/{cuid}

[[SECTION]]
UID: GSSC-BLLR-RESEARCH-TOOLS-ITEM-GET
TITLE: GET

[REQUIREMENT]
UID: GSSC-BLLR-347
TITLE: Research Tool Get
STATEMENT: >>>
The GSSC Website Unified Backend SHALL return a research tool by cuid in the path, including title and reference link.
<<<
RATIONALE: >>>
Path cuid identifies one research tool for assembly or editing.
<<<
DERIVED: False
VERIFICATION_METHOD: Test
CHANGE_DRIVER: GSSC5-18
REVIEW_STATUS: Changed
RELATIONS:
- TYPE: Parent
  VALUE: GSSC-BHLR-189
  ROLE: Refines

[[/SECTION]]

[[SECTION]]
UID: GSSC-BLLR-RESEARCH-TOOLS-ITEM-PATCH
TITLE: PATCH

[REQUIREMENT]
UID: GSSC-BLLR-348
TITLE: Research Tool Modification
STATEMENT: >>>
The GSSC Website Unified Backend SHALL modify a research tool by cuid for a logged-in member who is a tool editor or an administrator, accepting title and reference link updates, and returning the updated tool's cuid, title, and reference link.
<<<
RATIONALE: >>>
Authorized editors keep tool titles and reference links current.
<<<
DERIVED: False
VERIFICATION_METHOD: Test
CHANGE_DRIVER: GSSC5-18
REVIEW_STATUS: Changed
RELATIONS:
- TYPE: Parent
  VALUE: GSSC-BHLR-191
  ROLE: Refines

[REQUIREMENT]
UID: GSSC-BLLR-351
TITLE: Research Tool Modification Forbidden
STATEMENT: >>>
The GSSC Website Unified Backend SHALL reject research tool modification without changing the research tool when the caller is not a tool editor and is not an administrator.
<<<
RATIONALE: >>>
Only tool editors and administrators may change research tools.
<<<
DERIVED: False
VERIFICATION_METHOD: Test
CHANGE_DRIVER: GSSC5-18
REVIEW_STATUS: Changed
RELATIONS:
- TYPE: Parent
  VALUE: GSSC-BHLR-191
  ROLE: Refines

[[/SECTION]]

[[SECTION]]
UID: GSSC-BLLR-RESEARCH-TOOLS-ITEM-DELETE
TITLE: DELETE

[REQUIREMENT]
UID: GSSC-BLLR-349
TITLE: Research Tool Deletion
STATEMENT: >>>
The GSSC Website Unified Backend SHALL delete a research tool by cuid for a logged-in member who is a tool editor or an administrator.
<<<
RATIONALE: >>>
Authorized editors remove tools that are no longer recommended.
<<<
DERIVED: False
VERIFICATION_METHOD: Test
CHANGE_DRIVER: GSSC5-18
REVIEW_STATUS: Changed
RELATIONS:
- TYPE: Parent
  VALUE: GSSC-BHLR-192
  ROLE: Refines

[REQUIREMENT]
UID: GSSC-BLLR-352
TITLE: Research Tool Deletion Forbidden
STATEMENT: >>>
The GSSC Website Unified Backend SHALL reject research tool deletion without deleting the research tool when the caller is not a tool editor and is not an administrator.
<<<
RATIONALE: >>>
Only tool editors and administrators may delete research tools.
<<<
DERIVED: False
VERIFICATION_METHOD: Test
CHANGE_DRIVER: GSSC5-18
REVIEW_STATUS: Changed
RELATIONS:
- TYPE: Parent
  VALUE: GSSC-BHLR-192
  ROLE: Refines

[[/SECTION]]

[[/SECTION]]

[[/SECTION]]

[[SECTION]]
UID: GSSC-BLLR-PUBLICATIONS-CATEGORY
TITLE: Publications

[[SECTION]]
UID: GSSC-BLLR-PUBLICATIONS-COLLECTION
TITLE: /publications

[[SECTION]]
UID: GSSC-BLLR-PUBLICATIONS-COLLECTION-GET
TITLE: GET

[REQUIREMENT]
UID: GSSC-BLLR-356
TITLE: Publications List
STATEMENT: >>>
The GSSC Website Unified Backend SHALL return each publication's cuid, title, reference link, and description when listing publications, with description null when that publication has no description.
<<<
RATIONALE: >>>
The public publications page assembles its hyperlink grid from this list, including optional description text under each title when present.
<<<
DERIVED: False
VERIFICATION_METHOD: Test
CHANGE_DRIVER: GSSC5-19
REVIEW_STATUS: Approved
RELATIONS:
- TYPE: Parent
  VALUE: GSSC-BHLR-195
  ROLE: Refines

[[/SECTION]]

[[SECTION]]
UID: GSSC-BLLR-PUBLICATIONS-COLLECTION-POST
TITLE: POST

[REQUIREMENT]
UID: GSSC-BLLR-357
TITLE: Publication Creation
STATEMENT: >>>
The GSSC Website Unified Backend SHALL create a publication for a logged-in member who is a publication editor or an administrator, requiring a title and a reference link, accepting an optional description, and returning the created publication's cuid, title, reference link, and description.
<<<
RATIONALE: >>>
Authorized editors add publications with the fields the public list presents. Description may be omitted.
<<<
DERIVED: False
VERIFICATION_METHOD: Test
CHANGE_DRIVER: GSSC5-19
REVIEW_STATUS: Approved
RELATIONS:
- TYPE: Parent
  VALUE: GSSC-BHLR-197
  ROLE: Refines

[REQUIREMENT]
UID: GSSC-BLLR-361
TITLE: Publication Creation Forbidden
STATEMENT: >>>
The GSSC Website Unified Backend SHALL reject publication creation without storing a publication when the caller is not a publication editor and is not an administrator.
<<<
RATIONALE: >>>
Only publication editors and administrators may add publications.
<<<
DERIVED: False
VERIFICATION_METHOD: Test
CHANGE_DRIVER: GSSC5-19
REVIEW_STATUS: Approved
RELATIONS:
- TYPE: Parent
  VALUE: GSSC-BHLR-197
  ROLE: Refines

[[/SECTION]]

[[/SECTION]]

[[SECTION]]
UID: GSSC-BLLR-PUBLICATIONS-ITEM
TITLE: /publications/{cuid}

[[SECTION]]
UID: GSSC-BLLR-PUBLICATIONS-ITEM-GET
TITLE: GET

[REQUIREMENT]
UID: GSSC-BLLR-358
TITLE: Publication Get
STATEMENT: >>>
The GSSC Website Unified Backend SHALL return a publication by cuid in the path, including title, reference link, and description, with description null when that publication has no description.
<<<
RATIONALE: >>>
Path cuid identifies one publication for assembly or editing.
<<<
DERIVED: False
VERIFICATION_METHOD: Test
CHANGE_DRIVER: GSSC5-19
REVIEW_STATUS: Approved
RELATIONS:
- TYPE: Parent
  VALUE: GSSC-BHLR-196
  ROLE: Refines

[[/SECTION]]

[[SECTION]]
UID: GSSC-BLLR-PUBLICATIONS-ITEM-PATCH
TITLE: PATCH

[REQUIREMENT]
UID: GSSC-BLLR-359
TITLE: Publication Modification
STATEMENT: >>>
The GSSC Website Unified Backend SHALL modify a publication by cuid for a logged-in member who is a publication editor or an administrator, accepting title, reference link, and description updates, and returning the updated publication's cuid, title, reference link, and description.
<<<
RATIONALE: >>>
Authorized editors keep publication fields current, including clearing or setting the optional description.
<<<
DERIVED: False
VERIFICATION_METHOD: Test
CHANGE_DRIVER: GSSC5-19
REVIEW_STATUS: Approved
RELATIONS:
- TYPE: Parent
  VALUE: GSSC-BHLR-198
  ROLE: Refines

[REQUIREMENT]
UID: GSSC-BLLR-362
TITLE: Publication Modification Forbidden
STATEMENT: >>>
The GSSC Website Unified Backend SHALL reject publication modification without changing the publication when the caller is not a publication editor and is not an administrator.
<<<
RATIONALE: >>>
Only publication editors and administrators may change publications.
<<<
DERIVED: False
VERIFICATION_METHOD: Test
CHANGE_DRIVER: GSSC5-19
REVIEW_STATUS: Approved
RELATIONS:
- TYPE: Parent
  VALUE: GSSC-BHLR-198
  ROLE: Refines

[[/SECTION]]

[[SECTION]]
UID: GSSC-BLLR-PUBLICATIONS-ITEM-DELETE
TITLE: DELETE

[REQUIREMENT]
UID: GSSC-BLLR-360
TITLE: Publication Deletion
STATEMENT: >>>
The GSSC Website Unified Backend SHALL delete a publication by cuid for a logged-in member who is a publication editor or an administrator.
<<<
RATIONALE: >>>
Authorized editors remove publications that are no longer listed.
<<<
DERIVED: False
VERIFICATION_METHOD: Test
CHANGE_DRIVER: GSSC5-19
REVIEW_STATUS: Approved
RELATIONS:
- TYPE: Parent
  VALUE: GSSC-BHLR-199
  ROLE: Refines

[REQUIREMENT]
UID: GSSC-BLLR-363
TITLE: Publication Deletion Forbidden
STATEMENT: >>>
The GSSC Website Unified Backend SHALL reject publication deletion without deleting the publication when the caller is not a publication editor and is not an administrator.
<<<
RATIONALE: >>>
Only publication editors and administrators may delete publications.
<<<
DERIVED: False
VERIFICATION_METHOD: Test
CHANGE_DRIVER: GSSC5-19
REVIEW_STATUS: Approved
RELATIONS:
- TYPE: Parent
  VALUE: GSSC-BHLR-199
  ROLE: Refines

[[/SECTION]]

[[/SECTION]]

[[/SECTION]]

[[SECTION]]
UID: GSSC-BLLR-NEWSLETTERS-CATEGORY
TITLE: Newsletters

[[SECTION]]
UID: GSSC-BLLR-NEWSLETTERS-COLLECTION
TITLE: /newsletters

[[SECTION]]
UID: GSSC-BLLR-NEWSLETTERS-COLLECTION-GET
TITLE: GET

[REQUIREMENT]
UID: GSSC-BLLR-387
TITLE: Newsletters List
STATEMENT: >>>
The GSSC Website Unified Backend SHALL return each newsletter's cuid, volume, number, month, year, file path, and keywords when listing newsletters, ordered from newest to oldest by year, then month, then volume, then number.
<<<
RATIONALE: >>>
The public newsletters page builds its selection menus from this ordered catalog.
<<<
DERIVED: False
VERIFICATION_METHOD: Test
CHANGE_DRIVER: GSSC5-20
REVIEW_STATUS: Approved
RELATIONS:
- TYPE: Parent
  VALUE: GSSC-BHLR-172
  ROLE: Refines

[REQUIREMENT]
UID: GSSC-BLLR-396
TITLE: Newsletters Keyword Filter
STATEMENT: >>>
The GSSC Website Unified Backend SHALL, when a keyword query is provided, limit the newsletter list to entries whose keywords include that keyword case-insensitively as a substring.
<<<
RATIONALE: >>>
Keywords support catalog search without a separate FE search surface.
<<<
DERIVED: False
VERIFICATION_METHOD: Test
CHANGE_DRIVER: GSSC5-20
REVIEW_STATUS: Approved
RELATIONS:
- TYPE: Parent
  VALUE: GSSC-BHLR-172
  ROLE: Refines

[[/SECTION]]

[[SECTION]]
UID: GSSC-BLLR-NEWSLETTERS-COLLECTION-POST
TITLE: POST

[REQUIREMENT]
UID: GSSC-BLLR-388
TITLE: Newsletter Creation
STATEMENT: >>>
The GSSC Website Unified Backend SHALL create a newsletter for a logged-in member who is a newsletter editor or an administrator, requiring volume, number, month, year, file path, and keywords, and returning the created newsletter's cuid and those fields.
<<<
RATIONALE: >>>
Authorized editors add catalog rows with the fields the public page presents.
<<<
DERIVED: False
VERIFICATION_METHOD: Test
CHANGE_DRIVER: GSSC5-20
REVIEW_STATUS: Approved
RELATIONS:
- TYPE: Parent
  VALUE: GSSC-BHLR-213
  ROLE: Refines

[REQUIREMENT]
UID: GSSC-BLLR-389
TITLE: Newsletter Creation Forbidden
STATEMENT: >>>
The GSSC Website Unified Backend SHALL reject newsletter creation without storing a newsletter when the caller is not a newsletter editor and is not an administrator.
<<<
RATIONALE: >>>
Only newsletter editors and administrators may add newsletters.
<<<
DERIVED: False
VERIFICATION_METHOD: Test
CHANGE_DRIVER: GSSC5-20
REVIEW_STATUS: Approved
RELATIONS:
- TYPE: Parent
  VALUE: GSSC-BHLR-213
  ROLE: Refines

[[/SECTION]]

[[/SECTION]]

[[SECTION]]
UID: GSSC-BLLR-NEWSLETTER-ITEM
TITLE: /newsletter/{cuid}

[[SECTION]]
UID: GSSC-BLLR-NEWSLETTER-ITEM-GET
TITLE: GET

[REQUIREMENT]
UID: GSSC-BLLR-390
TITLE: Newsletter Get
STATEMENT: >>>
The GSSC Website Unified Backend SHALL return a newsletter by cuid in the path, including volume, number, month, year, file path, and keywords.
<<<
RATIONALE: >>>
Path cuid identifies one newsletter for display or editing.
<<<
DERIVED: False
VERIFICATION_METHOD: Test
CHANGE_DRIVER: GSSC5-20
REVIEW_STATUS: Approved
RELATIONS:
- TYPE: Parent
  VALUE: GSSC-BHLR-173
  ROLE: Refines

[[/SECTION]]

[[SECTION]]
UID: GSSC-BLLR-NEWSLETTER-ITEM-PATCH
TITLE: PATCH

[REQUIREMENT]
UID: GSSC-BLLR-391
TITLE: Newsletter Modification
STATEMENT: >>>
The GSSC Website Unified Backend SHALL modify a newsletter by cuid for a logged-in member who is a newsletter editor or an administrator, accepting volume, number, month, year, file path, and keywords updates, and returning the updated newsletter.
<<<
RATIONALE: >>>
Authorized editors keep newsletter fields current.
<<<
DERIVED: False
VERIFICATION_METHOD: Test
CHANGE_DRIVER: GSSC5-20
REVIEW_STATUS: Approved
RELATIONS:
- TYPE: Parent
  VALUE: GSSC-BHLR-214
  ROLE: Refines

[REQUIREMENT]
UID: GSSC-BLLR-392
TITLE: Newsletter Modification Forbidden
STATEMENT: >>>
The GSSC Website Unified Backend SHALL reject newsletter modification without changing the newsletter when the caller is not a newsletter editor and is not an administrator.
<<<
RATIONALE: >>>
Only newsletter editors and administrators may change newsletters.
<<<
DERIVED: False
VERIFICATION_METHOD: Test
CHANGE_DRIVER: GSSC5-20
REVIEW_STATUS: Approved
RELATIONS:
- TYPE: Parent
  VALUE: GSSC-BHLR-214
  ROLE: Refines

[[/SECTION]]

[[SECTION]]
UID: GSSC-BLLR-NEWSLETTER-ITEM-DELETE
TITLE: DELETE

[REQUIREMENT]
UID: GSSC-BLLR-393
TITLE: Newsletter Deletion
STATEMENT: >>>
The GSSC Website Unified Backend SHALL delete a newsletter by cuid for a logged-in member who is a newsletter editor or an administrator.
<<<
RATIONALE: >>>
Authorized editors remove newsletters that are no longer listed.
<<<
DERIVED: False
VERIFICATION_METHOD: Test
CHANGE_DRIVER: GSSC5-20
REVIEW_STATUS: Approved
RELATIONS:
- TYPE: Parent
  VALUE: GSSC-BHLR-215
  ROLE: Refines

[REQUIREMENT]
UID: GSSC-BLLR-394
TITLE: Newsletter Deletion Forbidden
STATEMENT: >>>
The GSSC Website Unified Backend SHALL reject newsletter deletion without deleting the newsletter when the caller is not a newsletter editor and is not an administrator.
<<<
RATIONALE: >>>
Only newsletter editors and administrators may delete newsletters.
<<<
DERIVED: False
VERIFICATION_METHOD: Test
CHANGE_DRIVER: GSSC5-20
REVIEW_STATUS: Approved
RELATIONS:
- TYPE: Parent
  VALUE: GSSC-BHLR-215
  ROLE: Refines

[[/SECTION]]

[[/SECTION]]

[[/SECTION]]

[[SECTION]]
UID: GSSC-BLLR-FILES-CATEGORY
TITLE: Files

[[SECTION]]
UID: GSSC-BLLR-FILES-COLLECTION
TITLE: /files

[[SECTION]]
UID: GSSC-BLLR-FILES-COLLECTION-GET
TITLE: GET

[REQUIREMENT]
UID: GSSC-BLLR-371
TITLE: Directory List Parent
STATEMENT: >>>
The GSSC Website Unified Backend SHALL list the non-deleted child files and folders of the parent folder identified by the parent query parameter when listing files, treating a missing parent query parameter as the storage root.
<<<
RATIONALE: >>>
Callers name a directory by parent cuid or omit it to list the root.
<<<
DERIVED: False
VERIFICATION_METHOD: Test
CHANGE_DRIVER: GSSC5-71
REVIEW_STATUS: Approved
RELATIONS:
- TYPE: Parent
  VALUE: GSSC-BHLR-205
  ROLE: Refines

[REQUIREMENT]
UID: GSSC-BLLR-372
TITLE: Directory List Omits Soft-Deleted
STATEMENT: >>>
The GSSC Website Unified Backend SHALL omit soft-deleted files and folders from directory list results.
<<<
RATIONALE: >>>
Soft-deleted entries stay out of normal directory listings.
<<<
DERIVED: False
VERIFICATION_METHOD: Test
CHANGE_DRIVER: GSSC5-71
REVIEW_STATUS: Approved
RELATIONS:
- TYPE: Parent
  VALUE: GSSC-BHLR-205
  ROLE: Refines

[REQUIREMENT]
UID: GSSC-BLLR-373
TITLE: Directory List Read Access
STATEMENT: >>>
The GSSC Website Unified Backend SHALL include only child entries the caller may read when listing a directory, rejecting the list when the caller may not read the parent directory.
<<<
RATIONALE: >>>
List results follow read ACL metadata for the parent and each child.
<<<
DERIVED: False
VERIFICATION_METHOD: Test
CHANGE_DRIVER: GSSC5-71
REVIEW_STATUS: Approved
RELATIONS:
- TYPE: Parent
  VALUE: GSSC-BHLR-205
  ROLE: Refines

[REQUIREMENT]
UID: GSSC-BLLR-374
TITLE: Directory List Entry Fields
STATEMENT: >>>
The GSSC Website Unified Backend SHALL include cuid, name, kind, isPublic, readRoles, and writeRoles in each directory list entry.
<<<
RATIONALE: >>>
List entries carry identity, type, and ACL fields needed to navigate and authorize further requests.
<<<
DERIVED: False
VERIFICATION_METHOD: Test
CHANGE_DRIVER: GSSC5-71
REVIEW_STATUS: Approved
RELATIONS:
- TYPE: Parent
  VALUE: GSSC-BHLR-205
  ROLE: Refines

[REQUIREMENT]
UID: GSSC-BLLR-384
TITLE: Public File Read Access
STATEMENT: >>>
The GSSC Website Unified Backend SHALL treat a file or folder as readable by any caller when that entry's publicity flag is public and the entry is not soft-deleted.
<<<
RATIONALE: >>>
Public entries are available without a login.
<<<
DERIVED: False
VERIFICATION_METHOD: Test
CHANGE_DRIVER: GSSC5-71
REVIEW_STATUS: Approved
RELATIONS:
- TYPE: Parent
  VALUE: GSSC-BHLR-204
  ROLE: Refines
- TYPE: Parent
  VALUE: GSSC-BHLR-205
  ROLE: Refines

[REQUIREMENT]
UID: GSSC-BLLR-385
TITLE: Role File Read Access
STATEMENT: >>>
The GSSC Website Unified Backend SHALL treat a non-public file or folder as readable by a logged-in member when that member holds at least one role named in the entry's read role allow-list, or when that member is an administrator.
<<<
RATIONALE: >>>
Read allow-lists gate members-only entries; administrators retain read access.
<<<
DERIVED: False
VERIFICATION_METHOD: Test
CHANGE_DRIVER: GSSC5-71
REVIEW_STATUS: Approved
RELATIONS:
- TYPE: Parent
  VALUE: GSSC-BHLR-204
  ROLE: Refines
- TYPE: Parent
  VALUE: GSSC-BHLR-205
  ROLE: Refines

[[/SECTION]]

[[SECTION]]
UID: GSSC-BLLR-FILES-COLLECTION-POST
TITLE: POST

[REQUIREMENT]
UID: GSSC-BLLR-375
TITLE: Folder Creation
STATEMENT: >>>
The GSSC Website Unified Backend SHALL create a folder under the parent folder identified in the request for a caller with write access to that parent, requiring a name, inheriting the parent's access control when the request omits access control fields, and returning the created folder's cuid, name, kind, isPublic, readRoles, and writeRoles.
<<<
RATIONALE: >>>
Authorized writers create folders that start with the parent's ACL unless a non-loosening override is supplied.
<<<
DERIVED: False
VERIFICATION_METHOD: Test
CHANGE_DRIVER: GSSC5-71
REVIEW_STATUS: Approved
RELATIONS:
- TYPE: Parent
  VALUE: GSSC-BHLR-206
  ROLE: Refines

[REQUIREMENT]
UID: GSSC-BLLR-376
TITLE: Folder Creation Forbidden
STATEMENT: >>>
The GSSC Website Unified Backend SHALL reject folder creation without storing a folder when the caller lacks write access to the parent directory.
<<<
RATIONALE: >>>
Write ACL metadata gates folder creation.
<<<
DERIVED: False
VERIFICATION_METHOD: Test
CHANGE_DRIVER: GSSC5-71
REVIEW_STATUS: Approved
RELATIONS:
- TYPE: Parent
  VALUE: GSSC-BHLR-206
  ROLE: Refines

[REQUIREMENT]
UID: GSSC-BLLR-386
TITLE: Role File Write Access
STATEMENT: >>>
The GSSC Website Unified Backend SHALL treat a file or folder as writable by a logged-in member when that member holds at least one role named in the entry's write role allow-list, or when that member is an administrator.
<<<
RATIONALE: >>>
Write allow-lists gate uploads, folder creation, and soft deletion; administrators retain write access.
<<<
DERIVED: False
VERIFICATION_METHOD: Test
CHANGE_DRIVER: GSSC5-71
REVIEW_STATUS: Approved
RELATIONS:
- TYPE: Parent
  VALUE: GSSC-BHLR-202
  ROLE: Refines
- TYPE: Parent
  VALUE: GSSC-BHLR-203
  ROLE: Refines
- TYPE: Parent
  VALUE: GSSC-BHLR-206
  ROLE: Refines

[[/SECTION]]

[[/SECTION]]

[[SECTION]]
UID: GSSC-BLLR-FILES-UPLOAD
TITLE: /files/upload

[[SECTION]]
UID: GSSC-BLLR-FILES-UPLOAD-POST
TITLE: POST

[REQUIREMENT]
UID: GSSC-BLLR-377
TITLE: File Upload
STATEMENT: >>>
The GSSC Website Unified Backend SHALL store an uploaded file under the parent folder identified in the request for a caller with write access to that parent, writing the file bytes under the configured local storage root, inheriting the parent's access control when the request omits access control fields, and returning the created file's cuid, name, kind, isPublic, readRoles, and writeRoles.
<<<
RATIONALE: >>>
Authorized writers place file bytes into a directory with ACL inheritance by default.
<<<
DERIVED: False
VERIFICATION_METHOD: Test
CHANGE_DRIVER: GSSC5-71
REVIEW_STATUS: Approved
RELATIONS:
- TYPE: Parent
  VALUE: GSSC-BHLR-202
  ROLE: Refines

[REQUIREMENT]
UID: GSSC-BLLR-378
TITLE: File Upload Forbidden
STATEMENT: >>>
The GSSC Website Unified Backend SHALL reject file upload without storing a file when the caller lacks write access to the parent directory.
<<<
RATIONALE: >>>
Write ACL metadata gates uploads.
<<<
DERIVED: False
VERIFICATION_METHOD: Test
CHANGE_DRIVER: GSSC5-71
REVIEW_STATUS: Approved
RELATIONS:
- TYPE: Parent
  VALUE: GSSC-BHLR-202
  ROLE: Refines

[[/SECTION]]

[[/SECTION]]

[[SECTION]]
UID: GSSC-BLLR-FILES-ITEM
TITLE: /files/{cuid}

[[SECTION]]
UID: GSSC-BLLR-FILES-ITEM-GET
TITLE: GET

[REQUIREMENT]
UID: GSSC-BLLR-379
TITLE: File Get
STATEMENT: >>>
The GSSC Website Unified Backend SHALL return the stored file bytes for a file cuid in the path when the caller may read that file and the file is not soft-deleted.
<<<
RATIONALE: >>>
Path cuid identifies one file for download or preview.
<<<
DERIVED: False
VERIFICATION_METHOD: Test
CHANGE_DRIVER: GSSC5-71
REVIEW_STATUS: Approved
RELATIONS:
- TYPE: Parent
  VALUE: GSSC-BHLR-204
  ROLE: Refines

[REQUIREMENT]
UID: GSSC-BLLR-380
TITLE: File Get Denied
STATEMENT: >>>
The GSSC Website Unified Backend SHALL reject a file get without returning file bytes when the cuid is missing, names a folder, names a soft-deleted entry, or names a file the caller may not read.
<<<
RATIONALE: >>>
Missing, deleted, folder, and unauthorized targets stay closed.
<<<
DERIVED: False
VERIFICATION_METHOD: Test
CHANGE_DRIVER: GSSC5-71
REVIEW_STATUS: Approved
RELATIONS:
- TYPE: Parent
  VALUE: GSSC-BHLR-204
  ROLE: Refines

[[/SECTION]]

[[SECTION]]
UID: GSSC-BLLR-FILES-ITEM-DELETE
TITLE: DELETE

[REQUIREMENT]
UID: GSSC-BLLR-381
TITLE: File Soft Deletion
STATEMENT: >>>
The GSSC Website Unified Backend SHALL soft-delete a file or folder by cuid for a caller with write access to that entry by setting a soft-delete marker without removing stored file bytes from the filesystem as part of that soft deletion.
<<<
RATIONALE: >>>
Authorized writers hide entries while retaining bytes on disk.
<<<
DERIVED: False
VERIFICATION_METHOD: Test
CHANGE_DRIVER: GSSC5-71
REVIEW_STATUS: Approved
RELATIONS:
- TYPE: Parent
  VALUE: GSSC-BHLR-203
  ROLE: Refines

[REQUIREMENT]
UID: GSSC-BLLR-382
TITLE: File Soft Deletion Forbidden
STATEMENT: >>>
The GSSC Website Unified Backend SHALL reject soft deletion without marking the entry deleted when the caller lacks write access to that entry.
<<<
RATIONALE: >>>
Write ACL metadata gates soft deletion.
<<<
DERIVED: False
VERIFICATION_METHOD: Test
CHANGE_DRIVER: GSSC5-71
REVIEW_STATUS: Approved
RELATIONS:
- TYPE: Parent
  VALUE: GSSC-BHLR-203
  ROLE: Refines

[[/SECTION]]

[[/SECTION]]

[[/SECTION]]

[[/SECTION]]

[[/SECTION]]

[[SECTION]]
UID: GSSC-BLLR-DATA-STORAGE
TITLE: Data Storage

[[SECTION]]
UID: GSSC-BLLR-USERS
TITLE: Users

[REQUIREMENT]
UID: GSSC-BLLR-13
TITLE: Users Table
STATEMENT: >>>
The GSSC Website Unified Backend SHALL store each user in a users table.
<<<
RATIONALE: >>>
This story keeps each user record in a table. The columns of that table are the requirements under Users Table Fields.
<<<
DERIVED: False
VERIFICATION_METHOD: Test
CHANGE_DRIVER: GSSC5-33
REVIEW_STATUS: Approved
RELATIONS:
- TYPE: Parent
  VALUE: GSSC-BHLR-118
  ROLE: Refines

[[SECTION]]
UID: GSSC-BLLR-USERS-TABLE-FIELDS
TITLE: Users Table Fields

[REQUIREMENT]
UID: GSSC-BLLR-14
TITLE: User Username
STATEMENT: >>>
The GSSC Website Unified Backend SHALL store a Username for each user in the users table.
<<<
RATIONALE: >>>
Member login accepts a Username. No high-level requirement stores a Username. Each user record holds one.
<<<
DERIVED: True
VERIFICATION_METHOD: Test
CHANGE_DRIVER: GSSC5-33
REVIEW_STATUS: Approved

[REQUIREMENT]
UID: GSSC-BLLR-15
TITLE: User Primary Email
STATEMENT: >>>
The GSSC Website Unified Backend SHALL store a Primary Email for each user in the users table except the permanent admin account. The permanent admin account may have no Primary Email.
<<<
RATIONALE: >>>
Each user record holds the Primary Email used for login. A user account includes a Primary Email. The permanent admin account is the builtin admin account and may have no Primary Email.
<<<
DERIVED: False
VERIFICATION_METHOD: Test
CHANGE_DRIVER: GSSC5-33
REVIEW_STATUS: Approved
RELATIONS:
- TYPE: Parent
  VALUE: GSSC-BHLR-100
  ROLE: Refines
- TYPE: Parent
  VALUE: GSSC-BHLR-101
  ROLE: Refines

[REQUIREMENT]
UID: GSSC-BLLR-16
TITLE: User Secondary Email
STATEMENT: >>>
The GSSC Website Unified Backend SHALL store a Secondary Email for a user in the users table. The Secondary Email may be absent.
<<<
RATIONALE: >>>
Each user record can hold a Secondary Email. The Secondary Email may be absent.
<<<
DERIVED: False
VERIFICATION_METHOD: Test
CHANGE_DRIVER: GSSC5-33
REVIEW_STATUS: Approved
RELATIONS:
- TYPE: Parent
  VALUE: GSSC-BHLR-102
  ROLE: Refines

[REQUIREMENT]
UID: GSSC-BLLR-17
TITLE: User Password Hash
STATEMENT: >>>
The GSSC Website Unified Backend SHALL store the current password hash for each user in the users table.
<<<
RATIONALE: >>>
Each user record holds the hash used to check a login password. This requirement does not set the hash method.
<<<
DERIVED: False
VERIFICATION_METHOD: Test
CHANGE_DRIVER: GSSC5-33
REVIEW_STATUS: Approved
RELATIONS:
- TYPE: Parent
  VALUE: GSSC-BHLR-112
  ROLE: Refines

[REQUIREMENT]
UID: GSSC-BLLR-25
TITLE: User Cuid
STATEMENT: >>>
The GSSC Website Unified Backend SHALL store a generated cuid for each user in the users table. That cuid identifies the user on the user list, the user read, and the user update path.
<<<
RATIONALE: >>>
No high-level requirement names the identifier of a user record. The backend generates the cuid, and the user transactions use it to identify the user.
<<<
DERIVED: True
VERIFICATION_METHOD: Test
CHANGE_DRIVER: GSSC5-34
REVIEW_STATUS: Approved

[REQUIREMENT]
UID: GSSC-BLLR-26
TITLE: User First Name
STATEMENT: >>>
The GSSC Website Unified Backend SHALL store a First Name for a user in the users table. For a user other than the permanent admin, the First Name is non-empty.
<<<
RATIONALE: >>>
Each user record holds the First Name that the member can view and modify. The permanent admin account may omit it.
<<<
DERIVED: False
VERIFICATION_METHOD: Test
CHANGE_DRIVER: GSSC5-34
REVIEW_STATUS: Approved
RELATIONS:
- TYPE: Parent
  VALUE: GSSC-BHLR-96
  ROLE: Refines

[REQUIREMENT]
UID: GSSC-BLLR-27
TITLE: User Middle Name
STATEMENT: >>>
The GSSC Website Unified Backend SHALL store a Middle Name for a user in the users table. The Middle Name may be absent.
<<<
RATIONALE: >>>
Each user record can hold a Middle Name. A member may have no middle name, so the Middle Name may be absent.
<<<
DERIVED: False
VERIFICATION_METHOD: Test
CHANGE_DRIVER: GSSC5-34
REVIEW_STATUS: Approved
RELATIONS:
- TYPE: Parent
  VALUE: GSSC-BHLR-97
  ROLE: Refines
- TYPE: Parent
  VALUE: GSSC-BHLR-98
  ROLE: Refines

[REQUIREMENT]
UID: GSSC-BLLR-28
TITLE: User Last Name
STATEMENT: >>>
The GSSC Website Unified Backend SHALL store a Last Name for a user in the users table. For a user other than the permanent admin, the Last Name is non-empty.
<<<
RATIONALE: >>>
Each user record holds the Last Name that the member can view and modify. The permanent admin account may omit it.
<<<
DERIVED: False
VERIFICATION_METHOD: Test
CHANGE_DRIVER: GSSC5-34
REVIEW_STATUS: Approved
RELATIONS:
- TYPE: Parent
  VALUE: GSSC-BHLR-99
  ROLE: Refines

[REQUIREMENT]
UID: GSSC-BLLR-29
TITLE: User Primary Phone Number
STATEMENT: >>>
The GSSC Website Unified Backend SHALL store a Primary Phone Number for a user in the users table. For a user other than the permanent admin, the Primary Phone Number is non-empty.
<<<
RATIONALE: >>>
Each user record holds the Primary Phone Number that the member can view and modify. The permanent admin account may omit it.
<<<
DERIVED: False
VERIFICATION_METHOD: Test
CHANGE_DRIVER: GSSC5-34
REVIEW_STATUS: Approved
RELATIONS:
- TYPE: Parent
  VALUE: GSSC-BHLR-103
  ROLE: Refines
- TYPE: Parent
  VALUE: GSSC-BHLR-104
  ROLE: Refines

[REQUIREMENT]
UID: GSSC-BLLR-30
TITLE: User Secondary Phone Number
STATEMENT: >>>
The GSSC Website Unified Backend SHALL store a Secondary Phone Number for a user in the users table. The Secondary Phone Number may be absent.
<<<
RATIONALE: >>>
Each user record can hold a Secondary Phone Number. The Secondary Phone Number may be absent.
<<<
DERIVED: False
VERIFICATION_METHOD: Test
CHANGE_DRIVER: GSSC5-34
REVIEW_STATUS: Approved
RELATIONS:
- TYPE: Parent
  VALUE: GSSC-BHLR-105
  ROLE: Refines

[REQUIREMENT]
UID: GSSC-BLLR-31
TITLE: Secondary Phone Number Display
STATEMENT: >>>
The GSSC Website Unified Backend SHALL store whether a user's Secondary Phone Number is displayed. The other-member view includes the Secondary Phone Number when the user has chosen to display it and the Preferred Contact Method is Phone or None.
<<<
RATIONALE: >>>
The account holds the member's choice to display the Secondary Phone Number when one is provided. That choice puts the Secondary Phone Number in the other-member view when the Preferred Contact Method is Phone or None.
<<<
DERIVED: False
VERIFICATION_METHOD: Test
CHANGE_DRIVER: GSSC5-34
REVIEW_STATUS: Approved
RELATIONS:
- TYPE: Parent
  VALUE: GSSC-BHLR-116
  ROLE: Refines

[REQUIREMENT]
UID: GSSC-BLLR-32
TITLE: Secondary Email Display
STATEMENT: >>>
The GSSC Website Unified Backend SHALL store whether a user's Secondary Email is displayed. The other-member view includes the Secondary Email when the user has chosen to display it and the Preferred Contact Method is Email or None.
<<<
RATIONALE: >>>
The account holds the member's choice to display the Secondary Email when one is provided. That choice puts the Secondary Email in the other-member view when the Preferred Contact Method is Email or None.
<<<
DERIVED: False
VERIFICATION_METHOD: Test
CHANGE_DRIVER: GSSC5-34
REVIEW_STATUS: Approved
RELATIONS:
- TYPE: Parent
  VALUE: GSSC-BHLR-115
  ROLE: Refines

[REQUIREMENT]
UID: GSSC-BLLR-33
TITLE: User Preferred Contact Method
STATEMENT: >>>
The GSSC Website Unified Backend SHALL store a Preferred Contact Method for a user in the users table. The stored value is Email, Phone, or None. For a user other than the permanent admin, the Preferred Contact Method is present. The other-member view includes the Primary Email when the Preferred Contact Method is Email or None, and the Primary Phone Number when the Preferred Contact Method is Phone or None. An absent value provides no Primary Email and no Primary Phone Number in the other-member view.
<<<
RATIONALE: >>>
The account holds the Preferred Contact Method that the member can view and modify. The allowed values are Email, Phone, or None. Email shows the Primary Email, Phone shows the Primary Phone Number, and None shows both. The permanent admin account may omit it. An absent value gives the other-member view neither primary contact.
<<<
DERIVED: False
VERIFICATION_METHOD: Test
CHANGE_DRIVER: GSSC5-34
REVIEW_STATUS: Approved
RELATIONS:
- TYPE: Parent
  VALUE: GSSC-BHLR-106
  ROLE: Refines
- TYPE: Parent
  VALUE: GSSC-BHLR-11
  ROLE: Refines

[REQUIREMENT]
UID: GSSC-BLLR-34
TITLE: User Home Address
STATEMENT: >>>
The GSSC Website Unified Backend SHALL store a Home Address for a user in the users table as line 1, line 2, line 3, city, state, zip code, and zip extension. Line 1, city, state, and zip code are non-empty for a user other than the permanent admin. Line 2, line 3, and zip extension may be absent. The zip code is five digits. The zip extension, when present, is four digits. The permanent admin may omit the Home Address.
<<<
RATIONALE: >>>
The account holds the Home Address that the member can view and modify. Line 1, city, state, and the five-digit zip code are the required parts. Line 2, line 3, and the four-digit zip extension may be absent. The permanent admin account may omit the Home Address.
<<<
DERIVED: False
VERIFICATION_METHOD: Test
CHANGE_DRIVER: GSSC5-34
REVIEW_STATUS: Approved
RELATIONS:
- TYPE: Parent
  VALUE: GSSC-BHLR-107
  ROLE: Refines

[REQUIREMENT]
UID: GSSC-BLLR-35
TITLE: Home Address Display
STATEMENT: >>>
The GSSC Website Unified Backend SHALL store whether a user's Home Address is displayed in full or redacted. An absent choice, and a redacted choice, show the city and the state in the other-member view. A full choice shows the stored Home Address.
<<<
RATIONALE: >>>
The account holds the Home Address display that the member or an administrator can set. Redacted shows the city and the state. An absent choice is treated as redacted. A full choice shows the stored Home Address.
<<<
DERIVED: False
VERIFICATION_METHOD: Test
CHANGE_DRIVER: GSSC5-34
REVIEW_STATUS: Approved
RELATIONS:
- TYPE: Parent
  VALUE: GSSC-BHLR-117
  ROLE: Refines
- TYPE: Parent
  VALUE: GSSC-BHLR-12
  ROLE: Refines

[REQUIREMENT]
UID: GSSC-BLLR-36
TITLE: User Mailing Address
STATEMENT: >>>
The GSSC Website Unified Backend SHALL store a Mailing Address for a user in the users table in the same shape as the Home Address. Line 1, city, state, and zip code are non-empty for a user other than the permanent admin. Line 2, line 3, and zip extension may be absent. The zip code is five digits. The zip extension, when present, is four digits. The permanent admin may omit the Mailing Address. The Mailing Address has no view type.
<<<
RATIONALE: >>>
The account holds the Mailing Address that the member can view and modify. It uses the same parts as the Home Address. The Mailing Address has no full-or-redacted view type.
<<<
DERIVED: False
VERIFICATION_METHOD: Test
CHANGE_DRIVER: GSSC5-34
REVIEW_STATUS: Approved
RELATIONS:
- TYPE: Parent
  VALUE: GSSC-BHLR-108
  ROLE: Refines

[REQUIREMENT]
UID: GSSC-BLLR-37
TITLE: User is administrator
STATEMENT: >>>
The GSSC Website Unified Backend SHALL store is administrator for each user in the users table. is administrator is true or false. A user created before this column exists stores false unless that user is the permanent admin account created or updated by GSSC-BLLR-40.
<<<
RATIONALE: >>>
is administrator is the stored site privilege that makes a user an administrator. Existing users store false. The permanent admin account is set true by GSSC-BLLR-40.
<<<
DERIVED: False
VERIFICATION_METHOD: Test
CHANGE_DRIVER: GSSC5-34
REVIEW_STATUS: Approved
RELATIONS:
- TYPE: Parent
  VALUE: GSSC-BHLR-111
  ROLE: Refines

[REQUIREMENT]
UID: GSSC-BLLR-38
TITLE: User is user moderator
STATEMENT: >>>
The GSSC Website Unified Backend SHALL store is user moderator for each user in the users table. is user moderator is true or false. A user created before this column exists stores false.
<<<
RATIONALE: >>>
is user moderator is a stored site privilege. It is not the administrator privilege. Existing users store false.
<<<
DERIVED: False
VERIFICATION_METHOD: Test
CHANGE_DRIVER: GSSC5-34
REVIEW_STATUS: Approved
RELATIONS:
- TYPE: Parent
  VALUE: GSSC-BHLR-111
  ROLE: Refines

[REQUIREMENT]
UID: GSSC-BLLR-344
TITLE: User is tool editor
STATEMENT: >>>
The GSSC Website Unified Backend SHALL store is tool editor for each user in the users table. is tool editor is true or false. A user created before this column exists stores false.
<<<
RATIONALE: >>>
is tool editor is a stored site privilege that authorizes research tool catalog changes. Existing users store false.
<<<
DERIVED: False
VERIFICATION_METHOD: Test
CHANGE_DRIVER: GSSC5-18
REVIEW_STATUS: Changed
RELATIONS:
- TYPE: Parent
  VALUE: GSSC-BHLR-111
  ROLE: Refines

[REQUIREMENT]
UID: GSSC-BLLR-353
TITLE: Administrator Sets Tool Editor
STATEMENT: >>>
The GSSC Website Unified Backend SHALL let an administrator set is tool editor true or false on a member account.
<<<
RATIONALE: >>>
Administrators assign the tool editor privilege so authorized members can maintain the research tools catalog.
<<<
DERIVED: False
VERIFICATION_METHOD: Test
CHANGE_DRIVER: GSSC5-18
REVIEW_STATUS: Changed
RELATIONS:
- TYPE: Parent
  VALUE: GSSC-BHLR-111
  ROLE: Refines

[REQUIREMENT]
UID: GSSC-BLLR-355
TITLE: User is publication editor
STATEMENT: >>>
The GSSC Website Unified Backend SHALL store is publication editor for each user in the users table. is publication editor is true or false. A user created before this column exists stores false.
<<<
RATIONALE: >>>
is publication editor is a stored site privilege that authorizes publications catalog changes. Existing users store false.
<<<
DERIVED: False
VERIFICATION_METHOD: Test
CHANGE_DRIVER: GSSC5-19
REVIEW_STATUS: Approved
RELATIONS:
- TYPE: Parent
  VALUE: GSSC-BHLR-111
  ROLE: Refines

[REQUIREMENT]
UID: GSSC-BLLR-364
TITLE: Administrator Sets Publication Editor
STATEMENT: >>>
The GSSC Website Unified Backend SHALL let an administrator set is publication editor true or false on a member account.
<<<
RATIONALE: >>>
Administrators assign the publication editor privilege so authorized members can maintain the publications catalog.
<<<
DERIVED: False
VERIFICATION_METHOD: Test
CHANGE_DRIVER: GSSC5-19
REVIEW_STATUS: Approved
RELATIONS:
- TYPE: Parent
  VALUE: GSSC-BHLR-111
  ROLE: Refines

[REQUIREMENT]
UID: GSSC-BLLR-397
TITLE: User is newsletter editor
STATEMENT: >>>
The GSSC Website Unified Backend SHALL store is newsletter editor for each user in the users table. is newsletter editor is true or false. A user created before this column exists stores false.
<<<
RATIONALE: >>>
is newsletter editor is a stored site privilege that authorizes newsletters catalog changes and is separate from is publication editor. Existing users store false.
<<<
DERIVED: False
VERIFICATION_METHOD: Test
CHANGE_DRIVER: GSSC5-20
REVIEW_STATUS: Approved
RELATIONS:
- TYPE: Parent
  VALUE: GSSC-BHLR-111
  ROLE: Refines

[REQUIREMENT]
UID: GSSC-BLLR-398
TITLE: Administrator Sets Newsletter Editor
STATEMENT: >>>
The GSSC Website Unified Backend SHALL let an administrator set is newsletter editor true or false on a member account.
<<<
RATIONALE: >>>
Administrators assign the newsletter editor privilege so authorized members can maintain the newsletters catalog.
<<<
DERIVED: False
VERIFICATION_METHOD: Test
CHANGE_DRIVER: GSSC5-20
REVIEW_STATUS: Approved
RELATIONS:
- TYPE: Parent
  VALUE: GSSC-BHLR-111
  ROLE: Refines

[REQUIREMENT]
UID: GSSC-BLLR-64
TITLE: User Membership Status
STATEMENT: >>>
The GSSC Website Unified Backend SHALL store a Membership Status for a user in the users table. The Membership Status may be absent. This requirement does not name the status values.
<<<
RATIONALE: >>>
The account holds the member's Membership Status. The status may be absent. The allowed status values remain unnamed.
<<<
DERIVED: False
VERIFICATION_METHOD: Test
CHANGE_DRIVER: GSSC5-34
REVIEW_STATUS: Approved
RELATIONS:
- TYPE: Parent
  VALUE: GSSC-BHLR-114
  ROLE: Refines

[REQUIREMENT]
UID: GSSC-BLLR-275
TITLE: User Position
STATEMENT: >>>
The GSSC Website Unified Backend SHALL store a Position for a user in the users table. The Position may be absent. Empty is the default.
<<<
RATIONALE: >>>
Each user record can hold a Position. Empty is the default until Position is set. A populated Position is the member's leadership role. This requirement does not name the positions.
<<<
DERIVED: False
VERIFICATION_METHOD: Test
CHANGE_DRIVER: GSSC5-36
REVIEW_STATUS: Approved
RELATIONS:
- TYPE: Parent
  VALUE: GSSC-BHLR-110
  ROLE: Refines

[REQUIREMENT]
UID: GSSC-BLLR-276
TITLE: User Account Photo
STATEMENT: >>>
The GSSC Website Unified Backend SHALL store an Account Photo for a user in the users table. The Account Photo may be absent.
<<<
RATIONALE: >>>
Each user record can hold an Account Photo. The Account Photo may be absent. This requirement does not define the form of the photo or provide upload.
<<<
DERIVED: False
VERIFICATION_METHOD: Test
CHANGE_DRIVER: GSSC5-36
REVIEW_STATUS: Approved
RELATIONS:
- TYPE: Parent
  VALUE: GSSC-BHLR-109
  ROLE: Refines

[[/SECTION]]

[[SECTION]]
UID: GSSC-BLLR-USERS-TABLE-CONSTRAINTS
TITLE: Users Table Constraints

[REQUIREMENT]
UID: GSSC-BLLR-18
TITLE: Unique Username
STATEMENT: >>>
The GSSC Website Unified Backend SHALL associate each Username in the users table with one user.
<<<
RATIONALE: >>>
Login treats a Username as locating one user. Each stored Username belongs to one user.
<<<
DERIVED: True
VERIFICATION_METHOD: Test
CHANGE_DRIVER: GSSC5-33
REVIEW_STATUS: Approved

[REQUIREMENT]
UID: GSSC-BLLR-19
TITLE: Unique Primary Email
STATEMENT: >>>
The GSSC Website Unified Backend SHALL associate each Primary Email in the users table with one user.
<<<
RATIONALE: >>>
Login treats a Primary Email as locating one user. Each stored Primary Email belongs to one user.
<<<
DERIVED: True
VERIFICATION_METHOD: Test
CHANGE_DRIVER: GSSC5-33
REVIEW_STATUS: Approved

[[/SECTION]]

[[/SECTION]]

[[SECTION]]
UID: GSSC-BLLR-PASSWORD-HISTORY-STORE
TITLE: Password History

[REQUIREMENT]
UID: GSSC-BLLR-244
TITLE: Past Password Hash Rows
STATEMENT: >>>
The GSSC Website Unified Backend SHALL store each retained past password hash for a user in a password history table. Each row holds the password hash and links that hash to the user by the user's cuid.
<<<
RATIONALE: >>>
The backend stores past password hashes separately from the current hash and identifies the owning user by cuid.
<<<
DERIVED: False
VERIFICATION_METHOD: Test
CHANGE_DRIVER: GSSC5-35
REVIEW_STATUS: Approved
RELATIONS:
- TYPE: Parent
  VALUE: GSSC-BHLR-113
  ROLE: Refines

[REQUIREMENT]
UID: GSSC-BLLR-262
TITLE: Past Password Hash Creation Time
STATEMENT: >>>
The GSSC Website Unified Backend SHALL store the date and time of password creation on each past password hash row.
<<<
RATIONALE: >>>
The creation date and time identify which past hash is oldest when the history exceeds the configured count.
<<<
DERIVED: False
VERIFICATION_METHOD: Test
CHANGE_DRIVER: GSSC5-35
REVIEW_STATUS: Approved
RELATIONS:
- TYPE: Parent
  VALUE: GSSC-BHLR-113
  ROLE: Refines

[REQUIREMENT]
UID: GSSC-BLLR-261
TITLE: Past Password Hash Count Limit
STATEMENT: >>>
The GSSC Website Unified Backend SHALL delete the oldest past password hash rows by creation date and time when a user's password history exceeds the configured password history count.
<<<
RATIONALE: >>>
The backend keeps only the configured number of past password hashes for each user and drops the oldest first.
<<<
DERIVED: False
VERIFICATION_METHOD: Test
CHANGE_DRIVER: GSSC5-35
REVIEW_STATUS: Approved
RELATIONS:
- TYPE: Parent
  VALUE: GSSC-BHLR-113
  ROLE: Refines

[REQUIREMENT]
UID: GSSC-BLLR-245
TITLE: Password Recovery Token Rows
STATEMENT: >>>
The GSSC Website Unified Backend SHALL store each password recovery token hash in a password recovery tokens table. Each row holds the token hash, the user, the Primary Email paired with that token, the issue time, the expiry time, and a used marker.
<<<
RATIONALE: >>>
The backend stores recovery token hashes with the Primary Email and lifetime needed to complete recovery.
<<<
DERIVED: False
VERIFICATION_METHOD: Test
CHANGE_DRIVER: GSSC5-35
REVIEW_STATUS: Approved
RELATIONS:
- TYPE: Parent
  VALUE: GSSC-BHLR-161
  ROLE: Refines

[[/SECTION]]

[[SECTION]]
UID: GSSC-BLLR-KEY-VALUE-STORE
TITLE: Key-Value

[REQUIREMENT]
UID: GSSC-BLLR-306
TITLE: Key-Value Table
STATEMENT: >>>
The GSSC Website Unified Backend SHALL store each key-value entry in a key-value table.
<<<
RATIONALE: >>>
Global website data lives in a key-value table. The columns of that table are the requirements under Key-Value Store.
<<<
DERIVED: False
VERIFICATION_METHOD: Test
CHANGE_DRIVER: GSSC5-43
REVIEW_STATUS: Approved
RELATIONS:
- TYPE: Parent
  VALUE: GSSC-BHLR-119
  ROLE: Refines

[REQUIREMENT]
UID: GSSC-BLLR-307
TITLE: Key-Value Key
STATEMENT: >>>
The GSSC Website Unified Backend SHALL store a key for each key-value entry in the key-value table.
<<<
RATIONALE: >>>
Each entry is identified by its key.
<<<
DERIVED: False
VERIFICATION_METHOD: Test
CHANGE_DRIVER: GSSC5-43
REVIEW_STATUS: Approved
RELATIONS:
- TYPE: Parent
  VALUE: GSSC-BHLR-119
  ROLE: Refines

[REQUIREMENT]
UID: GSSC-BLLR-308
TITLE: Key-Value Value
STATEMENT: >>>
The GSSC Website Unified Backend SHALL store a value for each key-value entry in the key-value table.
<<<
RATIONALE: >>>
Each entry holds the value for its key.
<<<
DERIVED: False
VERIFICATION_METHOD: Test
CHANGE_DRIVER: GSSC5-43
REVIEW_STATUS: Approved
RELATIONS:
- TYPE: Parent
  VALUE: GSSC-BHLR-119
  ROLE: Refines

[[/SECTION]]

[[SECTION]]
UID: GSSC-BLLR-PAGE-DATA-STORAGE
TITLE: Generic Content

[REQUIREMENT]
UID: GSSC-BLLR-338
TITLE: Page Entry Table
STATEMENT: >>>
The GSSC Website Unified Backend SHALL store sections, announcements, and event details as rows in a page data table with a datatype, optional header, body, resources, tags, index, isPublic flag, create permission, modify permission, delete permission, and optional template reference.
<<<
RATIONALE: >>>
One table holds the three page data entry kinds with shared metadata including index and tags.
<<<
DERIVED: True
VERIFICATION_METHOD: Test
CHANGE_DRIVER: GSSC5-37
REVIEW_STATUS: Approved
RELATIONS:
- TYPE: Parent
  VALUE: GSSC-BHLR-185
  ROLE: Refines

[REQUIREMENT]
UID: GSSC-BLLR-339
TITLE: Page Entry Index
STATEMENT: >>>
The GSSC Website Unified Backend SHALL store an integer index on each page data table entry for sections, announcements, and event details.
<<<
RATIONALE: >>>
Index is unified across entry kinds that share a page.
<<<
DERIVED: True
VERIFICATION_METHOD: Test
CHANGE_DRIVER: GSSC5-37
REVIEW_STATUS: Approved
RELATIONS:
- TYPE: Parent
  VALUE: GSSC-BHLR-187
  ROLE: Refines

[REQUIREMENT]
UID: GSSC-BLLR-340
TITLE: Content Template Table
STATEMENT: >>>
The GSSC Website Unified Backend SHALL store each content template with a name, isPublic flag, tags, create permission, modify permission, and delete permission.
<<<
RATIONALE: >>>
Content templates persist the defaults applied when creating page data entries that use them.
<<<
DERIVED: True
VERIFICATION_METHOD: Test
CHANGE_DRIVER: GSSC5-37
REVIEW_STATUS: Approved
RELATIONS:
- TYPE: Parent
  VALUE: GSSC-BHLR-186
  ROLE: Refines

[REQUIREMENT]
UID: GSSC-BLLR-342
TITLE: Content Permission Bit Fields
STATEMENT: >>>
The GSSC Website Unified Backend SHALL interpret each non-administrator create, modify, and delete permission integer with bit 0 set for a regular member and bit 1 set for a user moderator.
<<<
RATIONALE: >>>
Permission integers on page data entries and content templates encode which non-administrator roles may create, modify, or delete.
<<<
DERIVED: True
VERIFICATION_METHOD: Test
CHANGE_DRIVER: GSSC5-37
REVIEW_STATUS: Approved
RELATIONS:
- TYPE: Parent
  VALUE: GSSC-BHLR-185
  ROLE: Refines

[[/SECTION]]

[[SECTION]]
UID: GSSC-BLLR-RESEARCH-TOOLS-STORAGE
TITLE: Research Tools

[REQUIREMENT]
UID: GSSC-BLLR-343
TITLE: Research Tools Table
STATEMENT: >>>
The GSSC Website Unified Backend SHALL store each research tool as a row in a research tools table with a cuid, a title, and a reference link.
<<<
RATIONALE: >>>
The dedicated table is the source of truth for the public research tools list.
<<<
DERIVED: False
VERIFICATION_METHOD: Test
CHANGE_DRIVER: GSSC5-18
REVIEW_STATUS: Changed
RELATIONS:
- TYPE: Parent
  VALUE: GSSC-BHLR-194
  ROLE: Refines

[[/SECTION]]

[[SECTION]]
UID: GSSC-BLLR-PUBLICATIONS-STORAGE
TITLE: Publications

[REQUIREMENT]
UID: GSSC-BLLR-354
TITLE: Publications Table
STATEMENT: >>>
The GSSC Website Unified Backend SHALL store each publication as a row in a publications table with a cuid, a title, a reference link, and an optional description.
<<<
RATIONALE: >>>
The dedicated table is the source of truth for the public publications list. Description may be absent.
<<<
DERIVED: False
VERIFICATION_METHOD: Test
CHANGE_DRIVER: GSSC5-19
REVIEW_STATUS: Approved
RELATIONS:
- TYPE: Parent
  VALUE: GSSC-BHLR-201
  ROLE: Refines

[[/SECTION]]

[[SECTION]]
UID: GSSC-BLLR-NEWSLETTERS-STORAGE
TITLE: Newsletters

[REQUIREMENT]
UID: GSSC-BLLR-395
TITLE: Newsletters Table
STATEMENT: >>>
The GSSC Website Unified Backend SHALL store each newsletter as a row in a newsletters table with a cuid, an integer volume, an integer number, an integer month, an integer year, a file path string, and keywords as a string array.
<<<
RATIONALE: >>>
The dedicated table is the source of truth for the public newsletters catalog. File path identifies the stored file for issue bytes.
<<<
DERIVED: False
VERIFICATION_METHOD: Test
CHANGE_DRIVER: GSSC5-20
REVIEW_STATUS: Approved
RELATIONS:
- TYPE: Parent
  VALUE: GSSC-BHLR-216
  ROLE: Refines

[[/SECTION]]

[[SECTION]]
UID: GSSC-BLLR-FILE-STORAGE
TITLE: File Storage

[REQUIREMENT]
UID: GSSC-BLLR-365
TITLE: File Storage Root Configuration
STATEMENT: >>>
The GSSC Website Unified Backend SHALL take the local file storage root directory from backend configuration key FILE_STORAGE_ROOT. The root defaults to ./data/files.
<<<
RATIONALE: >>>
Uploaded bytes are written under this configurable root on the local filesystem.
<<<
DERIVED: False
VERIFICATION_METHOD: Test
CHANGE_DRIVER: GSSC5-71
REVIEW_STATUS: Approved
RELATIONS:
- TYPE: Parent
  VALUE: GSSC-BHLR-207
  ROLE: Refines

[REQUIREMENT]
UID: GSSC-BLLR-366
TITLE: Stored File Entries Table
STATEMENT: >>>
The GSSC Website Unified Backend SHALL store each file and each folder as a row with a cuid, a name, a kind of file or folder, an optional parent folder cuid, a publicity flag, a read role allow-list, a write role allow-list, and an optional soft-delete marker.
<<<
RATIONALE: >>>
The table is the source of truth for directory metadata and ACL checks.
<<<
DERIVED: False
VERIFICATION_METHOD: Test
CHANGE_DRIVER: GSSC5-71
REVIEW_STATUS: Approved
RELATIONS:
- TYPE: Parent
  VALUE: GSSC-BHLR-208
  ROLE: Refines
- TYPE: Parent
  VALUE: GSSC-BHLR-209
  ROLE: Refines
- TYPE: Parent
  VALUE: GSSC-BHLR-212
  ROLE: Refines

[REQUIREMENT]
UID: GSSC-BLLR-367
TITLE: File ACL Role Tokens
STATEMENT: >>>
The GSSC Website Unified Backend SHALL interpret file and folder role allow-list entries as the role tokens member, userMod, toolEditor, and publicationEditor.
<<<
RATIONALE: >>>
These tokens map to site privileges used when checking read and write access.
<<<
DERIVED: False
VERIFICATION_METHOD: Test
CHANGE_DRIVER: GSSC5-71
REVIEW_STATUS: Approved
RELATIONS:
- TYPE: Parent
  VALUE: GSSC-BHLR-209
  ROLE: Refines

[REQUIREMENT]
UID: GSSC-BLLR-368
TITLE: File ACL Inheritance on Create
STATEMENT: >>>
The GSSC Website Unified Backend SHALL set a new file or folder's publicity flag, read role allow-list, and write role allow-list from its parent folder when the create request omits those access control fields.
<<<
RATIONALE: >>>
Omitted ACL fields inherit from the parent so children match the directory by default.
<<<
DERIVED: False
VERIFICATION_METHOD: Test
CHANGE_DRIVER: GSSC5-71
REVIEW_STATUS: Approved
RELATIONS:
- TYPE: Parent
  VALUE: GSSC-BHLR-210
  ROLE: Refines

[REQUIREMENT]
UID: GSSC-BLLR-369
TITLE: File ACL Non-Loosening Enforcement
STATEMENT: >>>
The GSSC Website Unified Backend SHALL reject creating or updating a file or folder when the requested publicity flag is public while the parent is not public, when the requested read role allow-list contains a role absent from the parent's read role allow-list, or when the requested write role allow-list contains a role absent from the parent's write role allow-list.
<<<
RATIONALE: >>>
Children may tighten access but must not grant broader access than the parent.
<<<
DERIVED: False
VERIFICATION_METHOD: Test
CHANGE_DRIVER: GSSC5-71
REVIEW_STATUS: Approved
RELATIONS:
- TYPE: Parent
  VALUE: GSSC-BHLR-211
  ROLE: Refines

[REQUIREMENT]
UID: GSSC-BLLR-370
TITLE: Soft-Delete Marker Retention
STATEMENT: >>>
The GSSC Website Unified Backend SHALL record soft deletion by setting the soft-delete marker on the entry while leaving that entry's file bytes on the local filesystem as part of soft deletion.
<<<
RATIONALE: >>>
Soft deletion is a metadata change; bytes remain under the storage root.
<<<
DERIVED: False
VERIFICATION_METHOD: Test
CHANGE_DRIVER: GSSC5-71
REVIEW_STATUS: Approved
RELATIONS:
- TYPE: Parent
  VALUE: GSSC-BHLR-203
  ROLE: Refines
- TYPE: Parent
  VALUE: GSSC-BHLR-212
  ROLE: Refines

[REQUIREMENT]
UID: GSSC-BLLR-383
TITLE: Administrator File ACL Bypass
STATEMENT: >>>
The GSSC Website Unified Backend SHALL treat an administrator as having read access and write access to every file and every folder.
<<<
RATIONALE: >>>
Administrators retain full control over stored files regardless of role allow-lists.
<<<
DERIVED: False
VERIFICATION_METHOD: Test
CHANGE_DRIVER: GSSC5-71
REVIEW_STATUS: Approved
RELATIONS:
- TYPE: Parent
  VALUE: GSSC-BHLR-209
  ROLE: Refines

[[/SECTION]]

[[/SECTION]]

[[SECTION]]
UID: GSSC-BLLR-MAIL-CONFIGURATION
TITLE: Mail Configuration

[REQUIREMENT]
UID: GSSC-BLLR-246
TITLE: SMTP Configuration
STATEMENT: >>>
The GSSC Website Unified Backend SHALL take SMTP host, SMTP port, SMTP credentials, and SMTP from address from backend configuration. The SMTP host and credentials and from address default to empty. The SMTP port defaults to 587.
<<<
RATIONALE: >>>
Password recovery mail uses configured SMTP settings. An empty host leaves the backend unable to complete sending.
<<<
DERIVED: True
VERIFICATION_METHOD: Test
CHANGE_DRIVER: GSSC5-35
REVIEW_STATUS: Approved

[[/SECTION]]

[[SECTION]]
UID: GSSC-BLLR-WEB-SECURITY
TITLE: Web Security

[[SECTION]]
UID: GSSC-BLLR-PERMANENT-ADMIN
TITLE: Permanent Admin

[REQUIREMENT]
UID: GSSC-BLLR-20
TITLE: Admin Username
STATEMENT: >>>
The GSSC Website Unified Backend SHALL read the permanent admin username from the .env file. The username defaults to admin.
<<<
RATIONALE: >>>
The permanent admin account takes its username from the .env file. No high-level requirement defines this account.
<<<
DERIVED: True
VERIFICATION_METHOD: Test
CHANGE_DRIVER: GSSC5-33
REVIEW_STATUS: Approved

[REQUIREMENT]
UID: GSSC-BLLR-21
TITLE: Admin Password
STATEMENT: >>>
The GSSC Website Unified Backend SHALL read the permanent admin password from the .env file. The password defaults to 1234.
<<<
RATIONALE: >>>
The permanent admin account takes its password from the .env file. No high-level requirement defines this account.
<<<
DERIVED: True
VERIFICATION_METHOD: Test
CHANGE_DRIVER: GSSC5-33
REVIEW_STATUS: Approved

[REQUIREMENT]
UID: GSSC-BLLR-22
TITLE: Admin Account Enabled
STATEMENT: >>>
The GSSC Website Unified Backend SHALL read a flag from the .env file that enables the permanent admin account. The flag defaults to false.
<<<
RATIONALE: >>>
The .env file decides whether the permanent admin account is created. The flag defaults to false.
<<<
DERIVED: True
VERIFICATION_METHOD: Test
CHANGE_DRIVER: GSSC5-33
REVIEW_STATUS: Approved

[REQUIREMENT]
UID: GSSC-BLLR-23
TITLE: Permanent Admin Account
STATEMENT: >>>
The GSSC Website Unified Backend SHALL create a permanent admin account when the .env flag enables it. The account is a user with the configured username, a current password hash of the configured password, and the configured admin email when that email is provided. The admin email is read from the .env file and defaults to empty. An empty admin email leaves the Primary Email unset. When the configured username already exists, the backend replaces that user's password hash and leaves the Primary Email and Secondary Email unchanged.
<<<
RATIONALE: >>>
No high-level requirement defines this account. The account is a user so the configured admin can log in. This requirement does not set the hash method. The Secondary Email is unset. The Primary Email is the configured admin email, and the permanent admin email is unset unless it is provided. An existing user keeps both email values when the password hash is replaced.
<<<
DERIVED: True
VERIFICATION_METHOD: Test
CHANGE_DRIVER: GSSC5-33
REVIEW_STATUS: Approved

[REQUIREMENT]
UID: GSSC-BLLR-24
TITLE: Admin Account Disabled
STATEMENT: >>>
The GSSC Website Unified Backend SHALL leave the permanent admin account uncreated when the .env flag is disabled. When that account already exists, the backend leaves the user and the user's password hash unchanged.
<<<
RATIONALE: >>>
The flag defaults to false, so the permanent admin account is not created unless the flag enables it. Disabling the flag leaves an existing permanent admin account in place and does not change its password hash.
<<<
DERIVED: True
VERIFICATION_METHOD: Test
CHANGE_DRIVER: GSSC5-33
REVIEW_STATUS: Approved

[REQUIREMENT]
UID: GSSC-BLLR-39
TITLE: Permanent Admin Field Exceptions
STATEMENT: >>>
The GSSC Website Unified Backend SHALL allow the permanent admin account to omit First Name, Last Name, Primary Phone Number, Preferred Contact Method, Home Address, and Mailing Address. The backend adds no .env configuration for account fields beyond the permanent admin username, email, password, and enable flag.
<<<
RATIONALE: >>>
No high-level requirement defines the permanent admin account. That account may omit the account fields this story adds. Configuration stays the username, email, password, and enable flag already defined for the account.
<<<
DERIVED: True
VERIFICATION_METHOD: Test
CHANGE_DRIVER: GSSC5-34
REVIEW_STATUS: Approved

[REQUIREMENT]
UID: GSSC-BLLR-40
TITLE: Permanent Admin is administrator
STATEMENT: >>>
The GSSC Website Unified Backend SHALL store is administrator true and is user moderator false when the permanent admin account is created. When startup replaces that user's password hash because the configured username already exists, the backend sets is administrator true and leaves is user moderator unchanged.
<<<
RATIONALE: >>>
No high-level requirement defines the permanent admin account. The account is an administrator when it is created, and startup keeps is administrator true when it replaces the password hash. is user moderator stays false on create and is left as stored when the password hash is replaced.
<<<
DERIVED: True
VERIFICATION_METHOD: Test
CHANGE_DRIVER: GSSC5-34
REVIEW_STATUS: Approved

[[/SECTION]]

[[/SECTION]]
